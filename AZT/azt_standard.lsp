(defun azt_standard_start ()
    (if (equal azt_aktualna_skala_blokow nil)
      (setq azt_aktualna_skala_blokow "1")
      (princ "")
  )
)

(defun azt_wstaw_kote_start ()
  (setq azt_wstaw_kote_aktualny_poziom "0.000")
  (setq azt_wstaw_kote_aktualny_punkt_odniesienia "0.000")
)

(defun c:azt_skala_1 ()
  (setq azt_aktualna_skala_blokow "1")
  (command "-dimstyle" "_R" "ST_KR_1")
  (command "_setvar" "CMLEADERSTYLE" "ST_KR_1")
)

(defun c:azt_skala_5 ()
  (setq azt_aktualna_skala_blokow "5")
  (command "-dimstyle" "_R" "ST_KR_5")
  (command "_setvar" "CMLEADERSTYLE" "ST_KR_5")
)

(defun c:azt_skala_10 ()
  (setq azt_aktualna_skala_blokow "10")
  (command "-dimstyle" "_R" "ST_KR_10")
  (command "_setvar" "CMLEADERSTYLE" "ST_KR_10")
)

(defun c:azt_skala_20 ()
  (setq azt_aktualna_skala_blokow "20")
  (command "-dimstyle" "_R" "ST_KR_20")
  (command "_setvar" "CMLEADERSTYLE" "ST_KR_20")
)

(defun c:azt_skala_50 ()
  (setq azt_aktualna_skala_blokow "50")
  (command "-dimstyle" "_R" "ST_KR_50")
  (command "_setvar" "CMLEADERSTYLE" "ST_KR_50")
)

(defun c:azt_skala_100 ()
  (setq azt_aktualna_skala_blokow "100")
  (command "-dimstyle" "_R" "ST_KR_100")
  (command "_setvar" "CMLEADERSTYLE" "ST_KR_100")
)

(defun c:azt_skala_200 ()
  (setq azt_aktualna_skala_blokow "200")
  (command "-dimstyle" "_R" "ST_KR_200")
  (command "_setvar" "CMLEADERSTYLE" "ST_KR_200")
)


(defun c:azt_wstaw_maly_mtext ()
  (command "-layer" "_S" "S_TEXT" "")
  (setvar "TEXTSTYLE" "ARIAL NARROW")
  
  (if (equal azt_aktualna_skala_blokow "1")
      (setq azt_aktualna_wysokosc_tekstu "2")
      (princ "")
  )
  (if (equal azt_aktualna_skala_blokow "5")
      (setq azt_aktualna_wysokosc_tekstu "10")
      (princ "")
  )
  (if (equal azt_aktualna_skala_blokow "10")
      (setq azt_aktualna_wysokosc_tekstu "20")
      (princ "")
  )
  (if (equal azt_aktualna_skala_blokow "20")
      (setq azt_aktualna_wysokosc_tekstu "40")
      (princ "")
  )
  (if (equal azt_aktualna_skala_blokow "50")
      (setq azt_aktualna_wysokosc_tekstu "100")
      (princ "")
  )
  (if (equal azt_aktualna_skala_blokow "100")
      (setq azt_aktualna_wysokosc_tekstu "200")
      (princ "")
  )
  (if (equal azt_aktualna_skala_blokow "200")
      (setq azt_aktualna_wysokosc_tekstu "40")
      (princ "")
  )
  
  (setq azt_punkt_wstwienia_mtextu (getpoint "\nPodaj punkt wstawienia tekstu: "))
  (command "_mtext" azt_punkt_wstwienia_mtextu "_H" azt_aktualna_wysokosc_tekstu azt_punkt_wstwienia_mtextu "\n" "")
  (command "_mtedit" (entlast))
)

(defun c:azt_wstaw_sredni_mtext ()
  (command "-layer" "_S" "S_TEXT" "")
  (setvar "TEXTSTYLE" "ARIAL NARROW")
  
  (if (equal azt_aktualna_skala_blokow "1")
      (setq azt_aktualna_wysokosc_tekstu "2.5")
      (princ "")
  )
  (if (equal azt_aktualna_skala_blokow "5")
      (setq azt_aktualna_wysokosc_tekstu "12.5")
      (princ "")
  )
  (if (equal azt_aktualna_skala_blokow "10")
      (setq azt_aktualna_wysokosc_tekstu "25")
      (princ "")
  )
  (if (equal azt_aktualna_skala_blokow "20")
      (setq azt_aktualna_wysokosc_tekstu "50")
      (princ "")
  )
  (if (equal azt_aktualna_skala_blokow "50")
      (setq azt_aktualna_wysokosc_tekstu "125")
      (princ "")
  )
  (if (equal azt_aktualna_skala_blokow "100")
      (setq azt_aktualna_wysokosc_tekstu "250")
      (princ "")
  )
  (if (equal azt_aktualna_skala_blokow "200")
      (setq azt_aktualna_wysokosc_tekstu "500")
      (princ "")
  )
  
  (setq azt_punkt_wstwienia_mtextu (getpoint "\nPodaj punkt wstawienia tekstu: "))
  (command "_mtext" azt_punkt_wstwienia_mtextu "_H" azt_aktualna_wysokosc_tekstu azt_punkt_wstwienia_mtextu "\n" "")
  (command "_mtedit" (entlast))
)

(defun c:azt_wstaw_duzy_mtext ()
  (command "-layer" "_S" "S_TEXT" "")
  (setvar "TEXTSTYLE" "ARIAL NARROW")
  
  (if (equal azt_aktualna_skala_blokow "1")
      (setq azt_aktualna_wysokosc_tekstu "3")
      (princ "")
  )
  (if (equal azt_aktualna_skala_blokow "5")
      (setq azt_aktualna_wysokosc_tekstu "15")
      (princ "")
  )
  (if (equal azt_aktualna_skala_blokow "10")
      (setq azt_aktualna_wysokosc_tekstu "30")
      (princ "")
  )
  (if (equal azt_aktualna_skala_blokow "20")
      (setq azt_aktualna_wysokosc_tekstu "60")
      (princ "")
  )
  (if (equal azt_aktualna_skala_blokow "50")
      (setq azt_aktualna_wysokosc_tekstu "150")
      (princ "")
  )
  (if (equal azt_aktualna_skala_blokow "100")
      (setq azt_aktualna_wysokosc_tekstu "300")
      (princ "")
  )
  (if (equal azt_aktualna_skala_blokow "200")
      (setq azt_aktualna_wysokosc_tekstu "600")
      (princ "")
  )
  
  (setq azt_punkt_wstwienia_mtextu (getpoint "\nPodaj punkt wstawienia tekstu: "))
  (command "_mtext" azt_punkt_wstwienia_mtextu "_H" azt_aktualna_wysokosc_tekstu azt_punkt_wstwienia_mtextu "\n" "")
  (command "_mtedit" (entlast))
)

(defun c:azt_wstaw_opis_rzutni ()
  
  (vl-load-com)
  (vl-cmdf "_.-insert" "C:\\AZT\\BLOCKS\\azt_opis_rzutni.dwg" '(0. 0. 0.) "" "" "" "")
  (vl-cmdf "_.erase" (entlast) "")
  
  (command "-layer" "_S" "S_TEXT" "")
  ;(command "-insert" "s_NR_POZ" (getpoint) azt_aktualna_skala_blokow "" "0")
  (command "-insert" "azt_opis_rzutni" (getpoint) azt_aktualna_skala_blokow "" "0")
)

(defun c:azt_wstaw_opis_przekroju ()
  
  (vl-load-com)
  (vl-cmdf "_.-insert" "C:\\AZT\\BLOCKS\\azt_opis_przekroju.dwg" '(0. 0. 0.) "" "" "" "" "")
  (vl-cmdf "_.erase" (entlast) "")
  
  (command "-layer" "_S" "S_TEXT" "")
  ;(command "-insert" "s_OPIS" (getpoint) azt_aktualna_skala_blokow "" "0")
  (command "-insert" "azt_opis_przekroju" (getpoint) azt_aktualna_skala_blokow "" "0")
)

(defun c:azt_wstaw_symbol_przekroju ()

  (vl-load-com)
  (vl-cmdf "_.-insert" "C:\\AZT\\BLOCKS\\azt_symbol_przekroju.dwg" '(0. 0. 0.) "" "" "" "" "")
  (vl-cmdf "_.erase" (entlast) "")

  (setq azt_attdia_wartosc_domyslna (getvar "ATTDIA"))
  (setvar "ATTDIA" 0)
  (setq azt_wstaw_symbol_przekroju_punkt1 (getpoint "\nWskaz pierwszy punkt przekroju: "))
  (setq azt_wstaw_symbol_przekroju_punkt2 (getpoint azt_wstaw_symbol_przekroju_punkt1 "\nWskaz drugi punkt przekroju: "))
  (setq azt_wstaw_symbol_przekroju_nazwa_przekroju (getstring "\Podaj pojedynczy symbol przekroju: "))
  (setq azt_wstaw_symbol_przekroju_odleglosc (distance azt_wstaw_symbol_przekroju_punkt1 azt_wstaw_symbol_przekroju_punkt2))
  (setq azt_wstaw_symbol_przekroju_kat (angle azt_wstaw_symbol_przekroju_punkt1 azt_wstaw_symbol_przekroju_punkt2))
  ;(command "-insert" "s_PRZEKRÓJ" azt_wstaw_symbol_przekroju_punkt1 azt_aktualna_skala_blokow "" (* 180 (/ azt_wstaw_symbol_przekroju_kat pi)) azt_wstaw_symbol_przekroju_nazwa_przekroju azt_wstaw_symbol_przekroju_nazwa_przekroju)
  (command "-insert" "azt_symbol_przekroju" azt_wstaw_symbol_przekroju_punkt1 azt_aktualna_skala_blokow "" (* 180 (/ azt_wstaw_symbol_przekroju_kat pi)) azt_wstaw_symbol_przekroju_nazwa_przekroju azt_wstaw_symbol_przekroju_nazwa_przekroju)
  (setq azt_znacznik_przekroju (vlax-ename->vla-object (cdr (assoc -1 (entget (entlast))))))
  (vla-put-value (car (vlax-invoke azt_znacznik_przekroju 'getdynamicblockproperties)) (vlax-make-variant azt_wstaw_symbol_przekroju_odleglosc (vlax-variant-type (vla-get-value (car (vlax-invoke azt_znacznik_przekroju 'getdynamicblockproperties))))))
  (setvar "ATTDIA" azt_attdia_wartosc_domyslna)
  (princ)
)

(defun c:azt_przypisz_warstwe ()
  (repeat 100
    (setvar "CECOLOR" "BYLAYER")
    (setvar "CELWEIGHT" -1)
    (setvar "CELTYPE" "BYLAYER")
    (setq azt_obiekt_do_zmiany_warstwy (entsel "\nWybierz obiekt do zmiany: "))
    (command "_laymch" azt_obiekt_do_zmiany_warstwy "" "" "_Y")
  )
)

(defun c:azt_przetnij_w_punkcie ()
  (repeat 100
    (command "_break" pause "_f" pause "@")
  )
)

(defun c:azt_prasa ()
   ;^C^C_UCS;;_move;_all;;0,0,1e99;;_move;_all;;0,0,-1e99;;
  (command "_move" "_all" "" "" "0,0,1e99" "_move" "_all" "" "" "0,0,-1e99")
)

(defun c:azt_wstaw_kote_gora ()
  (vl-load-com)
  (vl-cmdf "_.-insert" "C:\\AZT\\BLOCKS\\azt_kota_gora.dwg" '(0. 0. 0.) "" "" "" "")
  (vl-cmdf "_.erase" (entlast) "")
  
  (setq azt_attdia_wartosc_domyslna (getvar "ATTDIA"))
  (setvar "ATTDIA" 0)
  (setq azt_wstaw_kote_punkt_wstawienia (getpoint "\nWskaz punkt wstawienia koty wysokosciowej: "))
  (setq azt_wstaw_kote_kota_odniesienia (entsel "\nWskaz kote odniesienia lub ENTER: "))
  
  (if (= azt_wstaw_kote_kota_odniesienia nil)
	(setq azt_wstaw_kote_poziom (getstring (strcat "\nPodaj poziom konstrukcyjny: <" azt_wstaw_kote_aktualny_poziom ">")))
	(progn
	(setq azt_wstaw_kote_atrybuty (vlax-invoke (vlax-ename->vla-object (car azt_wstaw_kote_kota_odniesienia)) 'Getattributes))
	(setq azt_wstaw_kote_punkt_odniesienia (vla-get-textstring (nth 0 azt_wstaw_kote_atrybuty)))
	(setq azt_wstaw_kote_kota_odniesienia_punkt_wstawienia (rtos (caddr (assoc 10 (entget (car azt_wstaw_kote_kota_odniesienia))))))
	(setq azt_wstaw_kote_poziom (rtos (+ (atof azt_wstaw_kote_punkt_odniesienia) (/ (+ (atof azt_wstaw_kote_punkt_odniesienia) (- (atof (rtos (cadr azt_wstaw_kote_punkt_wstawienia))) (atof azt_wstaw_kote_kota_odniesienia_punkt_wstawienia))) 1000)) 2 3))
	)
  )
  
  (if (equal azt_wstaw_kote_poziom "")
      (setq azt_wstaw_kote_poziom azt_wstaw_kote_aktualny_poziom)
      (princ)
  )
  (setq azt_wstaw_kote_aktualny_poziom azt_wstaw_kote_poziom)
  
  
  (vl-cmdf "_.-insert" "azt_kota_gora" azt_wstaw_kote_punkt_wstawienia azt_aktualna_skala_blokow "" "" azt_wstaw_kote_poziom)
  (setvar "ATTDIA" azt_attdia_wartosc_domyslna)
  (princ)
)

(defun c:azt_wstaw_kote_dol ()
  (vl-load-com)
  (vl-cmdf "_.-insert" "C:\\AZT\\BLOCKS\\azt_kota_dol.dwg" '(0. 0. 0.) "" "" "" "")
  (vl-cmdf "_.erase" (entlast) "")
  
  (setq azt_attdia_wartosc_domyslna (getvar "ATTDIA"))
  (setvar "ATTDIA" 0)
  (setq azt_wstaw_kote_punkt_wstawienia (getpoint "\nWskaz punkt wstawienia koty wysokosciowej: "))
  (setq azt_wstaw_kote_kota_odniesienia (entsel "\nWskaz kote odniesienia lub ENTER: "))
  
  (if (= azt_wstaw_kote_kota_odniesienia nil)
	(setq azt_wstaw_kote_poziom (getstring (strcat "\nPodaj poziom konstrukcyjny: <" azt_wstaw_kote_aktualny_poziom ">")))
	(progn
	(setq azt_wstaw_kote_atrybuty (vlax-invoke (vlax-ename->vla-object (car azt_wstaw_kote_kota_odniesienia)) 'Getattributes))
	(setq azt_wstaw_kote_punkt_odniesienia (vla-get-textstring (nth 0 azt_wstaw_kote_atrybuty)))
	(setq azt_wstaw_kote_kota_odniesienia_punkt_wstawienia (rtos (caddr (assoc 10 (entget (car azt_wstaw_kote_kota_odniesienia))))))
	(setq azt_wstaw_kote_poziom (rtos (+ (atof azt_wstaw_kote_punkt_odniesienia) (/ (+ (atof azt_wstaw_kote_punkt_odniesienia) (- (atof (rtos (cadr azt_wstaw_kote_punkt_wstawienia))) (atof azt_wstaw_kote_kota_odniesienia_punkt_wstawienia))) 1000)) 2 3))
	)
  )
  
  (if (equal azt_wstaw_kote_poziom "")
      (setq azt_wstaw_kote_poziom azt_wstaw_kote_aktualny_poziom)
      (princ)
  )
  (setq azt_wstaw_kote_aktualny_poziom azt_wstaw_kote_poziom)
  
  
  (vl-cmdf "_.-insert" "azt_kota_dol" azt_wstaw_kote_punkt_wstawienia azt_aktualna_skala_blokow "" "" azt_wstaw_kote_poziom)
  (setvar "ATTDIA" azt_attdia_wartosc_domyslna)
  (princ)
)

(azt_standard_start)
(azt_wstaw_kote_start)
