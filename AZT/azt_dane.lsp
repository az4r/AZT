(defun zmiana_warstw_structural ()
  (command "-layer" "_S" "0" "")
  (setq stss (cadr (sssetfirst nil (ssget "_ALL" (list '(62 . 253))))))
  (command "_.CHPROP" stss "" "_LA" "S_HATCH" "")
  (setq stss (cadr (sssetfirst nil (ssget "_ALL" (list '(62 . 1) (cons 6 "ACAD_ISO02W100"))))))
  (command "_.CHPROP" stss "" "_LA" "S_VIEW HIDDEN" "")
  (command "_laymrg" "N" "ST_WIC" "" "N" "S_VIEW THIN" "Y")
  (command "_laymrg" "N" "ST_WIS" "" "N" "S_VIEW" "Y")
  (command "_laymrg" "N" "ST_WIG" "" "N" "S_VIEW SECTION" "Y")
  (command "_laymrg" "N" "ST_OSD" "" "N" "S_GRIDS" "Y")
  (command "_laymrg" "N" "ST_LPM" "" "N" "S_VIEW HIDDEN" "Y")
  (command "_laymrg" "N" "ST_LPD" "" "N" "S_CUT LINE" "Y")
  (command "_laymrg" "N" "ST_POM" "" "N" "S_HELPER LINE" "Y")
  (command "_laymrg" "N" "ST_REV" "" "N" "S_REVISION" "Y")
  (command "_laymrg" "N" "ST_VP" "" "N" "Defpoints" "Y")
  (command "_laymrg" "N" "ST_SZR" "" "N" "S_HATCH" "Y")
  (command "_laymrg" "N" "ST_DMLSH" "" "N" "S_DEMOLISH" "Y")
  (command "_laymrg" "N" "ST_xref" "" "N" "S_XREF" "Y")
  (command "_laymrg" "N" "ST_WYM" "" "N" "S_DIMENSION" "Y")
  (command "_laymrg" "N" "ST_TXC" "" "N" "S_TEXT" "Y")
  (command "_laymrg" "N" "ST_TXS" "" "N" "S_TEXT" "Y")
  (command "_laymrg" "N" "ST_TXG" "" "N" "S_TEXT" "Y")
  (command "_laymrg" "N" "ST_DSC" "" "N" "S_TEXT" "Y")
  (command "_laymrg" "N" "ST_GH5" "" "N" "S_GRIDS" "Y")
  (command "_laymrg" "N" "ST_GH10" "" "N" "S_GRIDS" "Y")
  (command "_laymrg" "N" "ST_GH20" "" "N" "S_GRIDS" "Y")
  (command "_laymrg" "N" "ST_GH50" "" "N" "S_GRIDS" "Y")
  (command "_laymrg" "N" "ST_GH100" "" "N" "S_GRIDS" "Y")
  (command "_laymrg" "N" "ST_GH200" "" "N" "S_GRIDS" "Y")
  (command "_laymrg" "N" "ST_EXISTING" "" "N" "S_HATCH" "Y")
  (setq stss (cadr (sssetfirst nil (ssget "_ALL"))))
  (command "_.CHPROP" stss "" "_C" "ByLayer" "")
  (command "_.CHPROP" stss "" "_LT" "ByLayer" "")
  (command "_.CHPROP" stss "" "_LW" "ByLayer" "")
  (print "Zakonczono aktualizacje warstw do nowych standardow")
)

;(defun zmiana_warstw_advance ()
  ;(setq avss (cadr (sssetfirst nil (ssget "_ALL" (list '(62 . 3))))))
  ;(command "_.CHPROP" avss "" "_LA" "S_VIEW" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 254))))))
  ;(command "_.CHPROP" avss "" "_LA" "S_VIEW" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 9))))))
  ;(command "_.CHPROP" avss "" "_LA" "S_HATCH" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 1))))))
  ;(command "_.CHPROP" avss "" "_LA" "S_GRIDS" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 7) (cons 6 "Continuous"))))))
  ;(command "_.CHPROP" avss "" "_LA" "S_CUT LINE" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 7) (cons 6 "ZIGZAG"))))))
  ;(command "_.CHPROP" avss "" "_LA" "S_CUT LINE" "")
  ;(command "_.CHPROP" avss "" "_C" "ByLayer" "")
  ;(command "_.CHPROP" avss "" "_LT" "ByLayer" "")
  ;(command "_.CHPROP" avss "" "_LW" "ByLayer" "")
  ;(setq avss (cadr (sssetfirst nil (ssget "_ALL" (list '(62 . 256) (cons 8 "0"))))))
  ;(command "_.CHPROP" avss "" "_LA" "S_HATCH" "")
  ;(command "_.CHPROP" avss "" "_C" "ByLayer" "")
  ;(command "_.CHPROP" avss "" "_LT" "ByLayer" "")
  ;(command "_.CHPROP" avss "" "_LW" "ByLayer" "")
  ;(if (and (setq n -1) (setq ss (ssget "_ALL" (list '(62 . 256) (cons 8 "S_HATCH")))))
    ;(while (setq ent (ssname ss (setq n (1+ n))))
      ;(command "-layer" "_S" "S_VIEW SECTION" "")
      ;(command  "_hatchedit"  ent  "_boundary"  "_polyline"  "_yes")
    ;)
  ;)
  ;(setq avss (cadr (sssetfirst nil (ssget "_ALL" (list '(62 . 7) (cons 8 "0"))))))
  ;(command "_erase" avss "")
  ;(setq avss (cadr (sssetfirst nil (ssget "_X" (list '(0 . "TEXT") (cons 7 "Simplex.shx"))))))
  ;(command "_erase" avss "")
  ;(print "Zakonczono podmiane warstw z Advance Steel")
;)

(defun zmiana_warstw_advance ()
  (setq azt_selekcja_as_yellow (ssget "X" (list (cons 62 2))))
  (setq azt_selekcja_as_axis (ssget "X" (list (cons 62 6) (cons 8 "Beams"))))
  (setq azt_selekcja_as_grids (ssget "X" (list (cons 62 6) (cons 8 "Grids"))))
  (setq azt_selekcja_as_cyan (ssget "X" (list (cons 62 4))))
  (setq azt_selekcja_as_green (ssget "X" (list (cons 62 3))))
  (setq azt_selekcja_as_8 (ssget "X" (list (cons 62 8))))
  (setq azt_selekcja_as_254 (ssget "X" (list (cons 62 254))))
  (command "_chprop" azt_selekcja_as_yellow "" "_LT" "ByLayer" "_C" "ByLayer" "_LA" "S_VIEW" "")
  (command "_chprop" azt_selekcja_as_axis "" "_LT" "ByLayer" "_C" "ByLayer" "_LA" "S_AXIS" "")
  (command "_chprop" azt_selekcja_as_grids "" "_LT" "ByLayer" "_C" "ByLayer" "_LA" "S_GRIDS" "")
  (command "_chprop" azt_selekcja_as_cyan "" "_LT" "ByLayer" "_C" "ByLayer" "_LA" "S_VIEW HIDDEN" "")
  (command "_chprop" azt_selekcja_as_green "" "_LT" "ByLayer" "_C" "ByLayer" "_LA" "S_VIEW SECTION" "")
  (command "_chprop" azt_selekcja_as_8 "" "_LT" "ByLayer" "_C" "ByLayer" "_LA" "S_HATCH" "")
  (command "_chprop" azt_selekcja_as_254 "" "_LT" "ByLayer" "_C" "ByLayer" "_LA" "S_VIEW" "")
  (print "Zakonczono podmiane warstw z Advance Steel")
)

(defun c:azt_zmw_st ()
   (zmiana_warstw_structural)
)

(defun c:azt_zmw_as ()
   (zmiana_warstw_advance)
)
