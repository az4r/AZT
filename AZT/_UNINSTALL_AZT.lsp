(command "CUIUNLOAD" "AZT")
(princ "\n###############################################################")
(princ "\n################### ODINSTALOWANO AZ TOOLBAR ##################")
(princ "\n###############################################################")
(princ)
