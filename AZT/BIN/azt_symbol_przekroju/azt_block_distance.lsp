(defun set:distance (blk dis)
  (vl-some '(lambda (x)
              (and (eq "Distance1" (vla-get-propertyname x)) (vlax-put x 'Value dis))
            )
           (vlax-invoke (vlax-ename->vla-object blk) 'getdynamicBlockproperties)
           )
) (vl-load-com)

;USAGE: (set:distance <BlockEntityName> <DistanceValue>)
;(vlax-ename->vla-object (entlast))
