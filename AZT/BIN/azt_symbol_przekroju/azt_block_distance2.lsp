(defun set:distance (blk dis)
  (vl-some '(lambda (x)
              (and (eq "Odległość" (vla-get-propertyname x)) (vlax-put x 'Value dis))
            )
           (vlax-invoke (vlax-ename->vla-object blk) 'getdynamicBlockproperties)
           )
) (vl-load-com)

;USAGE: (set:distance <BlockEntityName> <DistanceValue>)
(set:distance (vlax-ename->vla-object (entlast)) 50)
;(vlax-ename->vla-object (entlast))
