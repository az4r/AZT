;#######################   DANE WEJSCIOWE ##########################

(defun azt_sruba_start ()
  (setq azt_aktualna_sruba_widok_typ "12")
  (setq azt_aktualna_sruba_gwint_typ "12")
  (setq azt_aktualna_sruba_leb_typ "12")
  (princ)
)

(defun azt_profil_widok_start ()
  (setq azt_aktualna_rodzina_profil_widok "UPE")
  (setq azt_aktualny_typ_profil_widok "200")
)

;#######################   SRUBY - POCZATEK  #######################

(defun azt_skleszczenie_sruby ()
  (setq azt_aktualne_skleszczenie_sruby (getstring (strcat "\nPodaj skleszczenie sruby: <" (rtos (distance azt_punkt1_skleszczenia_sruby azt_punkt2_skleszczenia_sruby) 2 0) ">")))
  (if (equal azt_aktualne_skleszczenie_sruby "")
      (setq azt_aktualne_skleszczenie_sruby (rtos (distance azt_punkt1_skleszczenia_sruby azt_punkt2_skleszczenia_sruby) 2 0))
      (princ)
  )
  (setq azt_aktualne_skleszczenie_sruby (atof azt_aktualne_skleszczenie_sruby))
)

(defun azt_punkty_skleszczenia_sruby ()
  (setq azt_punkt1_skleszczenia_sruby (getpoint "\nWskaz punkt wstawienia sruby: "))
  (setq azt_punkt2_skleszczenia_sruby (getpoint azt_punkt1_skleszczenia_sruby "\nWskaz kierunek wstawienia sruby: "))
)

(defun azt_punkt_wstawienia_sruby_przekr ()
  (setq azt_punkt1_wstawienia_sruby_przekr (getpoint "\nWskaz punkt wstawienia sruby: "))
  (setq azt_punkt2_wstawienia_sruby_przekr '(10.0 0.0 0.0))
)

(defun azt_wprowadz_skleszczenie_sruby ()
  (setq azt_selekcja_sruby_st_nwid (cadr (sssetfirst nil (ssget "_ALL" (list '(62 . 126))))))
  (setq azt_selekcja_sruby_nwid (cadr (sssetfirst nil (ssget "_ALL" (list '(62 . 127))))))
  (setq azt_selekcja_sruby_wid (cadr (sssetfirst nil (ssget "_ALL" (list '(62 . 128))))))
  (command "_move" azt_selekcja_sruby_nwid "" '(0.0 0.0 0.0) (list azt_aktualne_skleszczenie_sruby 0.0 0.0))
  (command "_move" azt_selekcja_sruby_wid "" '(0.0 0.0 0.0) (list azt_aktualne_skleszczenie_sruby 0.0 0.0))
  (command "_chprop" azt_selekcja_sruby_st_nwid "" "_C" "ByLayer" "")
  (command "_chprop" azt_selekcja_sruby_wid "" "_C" "ByLayer" "")
  (command "_chprop" azt_selekcja_sruby_nwid "" "_C" "ByLayer" "")
  (command "_.CHPROP" azt_selekcja_sruby_st_nwid "" "_LA" "S_VIEW HIDDEN" "")
  (command "_.CHPROP" azt_selekcja_sruby_wid "" "_LA" "S_VIEW" "")
  (command "_.CHPROP" azt_selekcja_sruby_nwid "" "_LA" "S_VIEW HIDDEN" "")
)

(defun azt_ucs_sruby ()
  (command "_UCS" azt_punkt1_skleszczenia_sruby (trans azt_punkt2_skleszczenia_sruby 0 1) "")
)

(defun azt_ucs_wstawienia_sruby_przekr ()
  (command "_UCS" azt_punkt1_wstawienia_sruby_przekr azt_punkt2_wstawienia_sruby_przekr "")
)

(defun azt_przywroc_ucs_sruby ()
  (command "_UCS" "_World")
  (princ)
)

(defun c:azt_sruba_widok ()
  (setq azt_sruba_widok_typ (getstring (strcat "\nPodaj srednice trzpienia sruby (MXX): <" azt_aktualna_sruba_widok_typ ">")))
  (if (equal azt_sruba_widok_typ "")
      (setq azt_sruba_widok_typ azt_aktualna_sruba_widok_typ)
      (princ)
  )
  (if (equal azt_sruba_widok_typ "12")
      (c:azt_sruba_widok_m12)
      (princ)
  )
  (if (equal azt_sruba_widok_typ "16")
      (c:azt_sruba_widok_m16)
      (princ)
  )
  (princ)
)

(defun c:azt_sruba_gwint ()
(setq azt_sruba_gwint_typ (getstring (strcat "\nPodaj srednice trzpienia sruby (MXX): <" azt_aktualna_sruba_gwint_typ ">")))
  (if (equal azt_sruba_gwint_typ "")
      (setq azt_sruba_gwint_typ azt_aktualna_sruba_gwint_typ)
      (princ)
  )  
  (if (equal azt_sruba_gwint_typ "12")
      (c:azt_sruba_gwint_m12)
      (princ)
  )
  (if (equal azt_sruba_gwint_typ "16")
      (c:azt_sruba_gwint_m16)
      (princ)
  )
  (princ)
)

(defun c:azt_sruba_leb ()
(setq azt_sruba_leb_typ (getstring (strcat "\nPodaj srednice trzpienia sruby (MXX): <" azt_aktualna_sruba_leb_typ ">")))
  (if (equal azt_sruba_leb_typ "")
      (setq azt_sruba_leb_typ azt_aktualna_sruba_leb_typ)
      (princ)
  )  
  (if (equal azt_sruba_leb_typ "12")
      (c:azt_sruba_leb_m12)
      (princ)
  )
  (if (equal azt_sruba_leb_typ "16")
      (c:azt_sruba_leb_m16)
      (princ)
  )
  (princ)
)

;#######################   SRUBA M12   #######################
;#######################   SRUBA M12 - WIDOK   #######################

(defun azt_rysuj_leb_m12 ()
(command "_pline" '(-7.0000 -10.9500) '(0.0000 -10.9500) '(0.0000 10.9500) '(-7.0000 10.9500) "")
(command "_pline" '(-7.0000 5.4750) '(0.0000 5.4750) "")
(command "_pline" '(-7.0000 -5.4750) '(0.0000 -5.4750) "")
(command "_arc" '(-7.0000 10.9500) "_C" '(-3.7530 8.2125) '(-7.0000 5.4750))
(command "_arc" '(-7.0000 5.4750) "_C" '(4.7503 0.5000) '(-8.0000 0.0000))
(command "_arc" '(-8.0000 0.0000) "_C" '(4.7503 -0.5000) '(-7.0000 -5.4750))
(command "_arc" '(-7.0000 -5.4750) "_C" '(-3.7530 -8.2125) '(-7.0000 -10.9500))
(command "_pline" '(-8.0000 -8.2125) '(-8.0000 8.2125) "")
)

(defun azt_rysuj_trzpien_m12 ()
(command "_pline" '(0.0 6.0) (list azt_aktualne_skleszczenie_sruby 6.0 ) "")
(command "_pline" '(0.0 -6.0) (list azt_aktualne_skleszczenie_sruby -6.0 ) "")
)

(defun azt_rysuj_podkladki_m12 ()
(command "_pline" '(0.0000 -12.0000) '(5.0000 -12.0000) '(5.0000 -6.0000) '(0.0000 -6.0000) '(0.0000 -12.0000) "")
(command "_pline" '(0.0000 -6.5000) '(5.0000 -6.5000) "")
(command "_pline" '(2.5000 -12.0000) '(2.5000 -6.0000) "")
(command "_pline" '(0.0000 12.0000) '(0.0000 6.0000) '(5.0000 6.0000) '(5.0000 12.0000) '(0.0000 12.0000) "")
(command "_pline" '(0.0000 6.5000) '(5.0000 6.5000) "")
(command "_pline" '(2.5000 6.0000) '(2.5000 12.0000) "")
)

(defun azt_rysuj_nakretke_m12 ()
(command "_pline" '(6.0000 -10.9500) '(14.0000 -10.9500) "")
(command "_pline" '(6.0000 -5.4750) '(14.0000 -5.4750) "")
(command "_pline" '(6.0000 5.4750) '(14.0000 5.4750) "")
(command "_pline" '(6.0000 10.9500) '(14.0000 10.9500) "")
(command "_arc" '(6.0000 10.9500) "_C" '(9.2470 8.2125) '(6.0000 5.4750))
(command "_arc" '(6.0000 5.4750) "_C" '(17.7503 0.5000) '(5.0000 0.0000))
(command "_arc" '(5.0000 0.0000) "_C" '(17.7503 -0.5000) '(6.0000 -5.4750))
(command "_arc" '(6.0000 -5.4750) "_C" '(9.2470 -8.2125) '(6.0000 -10.9500))
(command "_arc" '(14.0000 -10.9500) "_C" '(10.7530 -8.2125) '(14.0000 -5.4750))
(command "_arc" '(14.0000 -5.4750) "_C" '(2.2497 -0.5000) '(15.0000 0.0000))
(command "_arc" '(15.0000 0.0000) "_C" '(2.2497 0.5000) '(14.0000 5.4750))
(command "_arc" '(14.0000 5.4750) "_C" '(10.7530 8.2125) '(14.0000 10.9500))
(command "_pline" '(5.0000 -8.2125) '(5.0000 8.2125) "")
(command "_pline" '(15.0000 -8.2125) '(15.0000 8.2125) "")
)

(defun azt_rysuj_gwint_m12 ()
  (command "_pline" '(15.0000 -6.0000) '(33.0000 -6.0000) '(35.0000 -4.0000) '(35.0000 4.0000) '(33.0000 6.0000) '(15.0000 6.0000) "")
)

(defun azt_rysuj_niewidoczna_czesc_sruby_m12 ()
(command "_pline" '(3.0000 -6.0000) '(5.0000 -4.0000) '(35.0000 -4.0000) "")
(command "_pline" '(3.0000 6.0000) '(5.0000 4.0000) '(35.0000 4.0000) "")
(command "_pline" '(33.0000 6.0000) '(33.0000 -6.0000) "")
(command "_pline" '(5.0000 -6.0000) '(5.0000 6.0000) "")
)

(defun c:azt_sruba_widok_m12 ()
  (setq azt_aktualna_sruba_widok_typ "12")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m12)
  (setvar "CECOLOR" "126")
  (azt_rysuj_trzpien_m12)
  (setvar "CECOLOR" "127")
  (azt_rysuj_niewidoczna_czesc_sruby_m12)
  (setvar "CECOLOR" "128")
  (azt_rysuj_podkladki_m12)
  (azt_rysuj_nakretke_m12)
  (azt_rysuj_gwint_m12)
  (azt_wprowadz_skleszczenie_sruby)
  (azt_przywroc_ucs_sruby)
  (command "_ZOOM" "_SCALE" "0.0001X")
  (command "_layer" "_S" "0" "")
  (setvar "CECOLOR" "BYLAYER")
)

;#######################   SRUBA M12 - GWINT   #######################

(defun azt_rysuj_gwint_przekr_m12 ()
(command "_circle" '(0.0000 0.0000) '(12.0000 0.0000))
(command "_circle" '(0.0000 0.0000) '(8.5000 0.0000))
(command "_circle" '(0.0000 0.0000) '(6.0000 0.0000))
(command "_pline" '(0.0000 -10.9500) '(9.5000 -5.4750) '(9.5000 5.4750) '(0.0000 10.9500) '(-9.5000 5.4750) '(-9.5000 -5.4750) '(0.0000 -10.9500) "")
)

(defun azt_rysuj_osie_gwint_przekr_m12 ()
(command "_pline" '(0.0000 -21.9000) '(0.0000 21.9000) "")
(command "_pline" '(-19.0000 0.0000) '(19.0000 0.0000) "")
)

(defun c:azt_sruba_gwint_m12 ()
(setq azt_aktualna_sruba_gwint_typ "12")
(azt_punkt_wstawienia_sruby_przekr)
(command "_ZOOM" "_SCALE" "10000X")
(azt_ucs_wstawienia_sruby_przekr)
(command "_layer" "_S" "S_VIEW" "")
(azt_rysuj_gwint_przekr_m12)
(command "_layer" "_S" "S_GRIDS" "")
(azt_rysuj_osie_gwint_przekr_m12)
(azt_przywroc_ucs_sruby)
(command "_ZOOM" "_SCALE" "0.0001X")
(command "_layer" "_S" "0" "")
)


;#######################   SRUBA M12 - LEB   #######################

(defun azt_rysuj_leb_przekr_m12 ()
(command "_circle" '(0.0000 0.0000) '(8.5000 0.0000))
(command "_pline" '(0.0000 -10.9500) '(9.5000 -5.4750) '(9.5000 5.4750) '(0.0000 10.9500) '(-9.5000 5.4750) '(-9.5000 -5.4750) '(0.0000 -10.9500) "")
)

(defun azt_rysuj_osie_leb_przekr_m12 ()
(command "_pline" '(0.0000 -21.9000) '(0.0000 21.9000) "")
(command "_pline" '(-19.0000 0.0000) '(19.0000 0.0000) "")
)

(defun c:azt_sruba_leb_m12 ()
(setq azt_aktualna_sruba_leb_typ "12")
(azt_punkt_wstawienia_sruby_przekr)
(command "_ZOOM" "_SCALE" "10000X")
(azt_ucs_wstawienia_sruby_przekr)
(command "_layer" "_S" "S_VIEW" "")
(azt_rysuj_leb_przekr_m12)
(command "_layer" "_S" "S_GRIDS" "")
(azt_rysuj_osie_leb_przekr_m12)
(azt_przywroc_ucs_sruby)
(command "_ZOOM" "_SCALE" "0.0001X")
(command "_layer" "_S" "0" "")
)

;#######################   KONIEC SRUBY M12   #######################

;#######################   SRUBA M16   #######################
;#######################   SRUBA M16 - WIDOK   #######################

(defun azt_rysuj_leb_m16 ()
  (command "_pline" '(-9.0000 -13.8500) '(0.0000 -13.8500) '(0.0000 13.8500) '(-9.0000 13.8500) "")
  (command "_pline" '(-9.0000 -6.9250) '(0.0000 -6.9250) "")
  (command "_pline" '(-9.0000 6.9250) '(0.0000 6.9250) "")
  (command "_arc" '(-9.0000 13.8500) "_C" '(-3.5055 10.3875) '(-9.0000 6.9250))
  (command "_arc" '(-9.0000 6.9250) "_C" '(11.0153 0.5000) '(-10.0000 0.0000))
  (command "_arc" '(-10.0000 0.0000) "_C" '(11.0153 -0.5000) '(-9.0000 -6.9250))
  (command "_arc" '(-9.0000 -6.9250) "_C" '(-3.5055 -10.3875) '(-9.0000 -13.8500))
  (command "_pline" '(-10.0000 -10.3875) '(-10.0000 10.3875) "")
)

(defun azt_rysuj_trzpien_m16 ()
(command "_pline" '(0.0 8.0) (list azt_aktualne_skleszczenie_sruby 8.0 ) "")
(command "_pline" '(0.0 -8.0) (list azt_aktualne_skleszczenie_sruby -8.0 ) "")
)

(defun azt_rysuj_podkladki_m16 ()
  (command "_pline" '(0.0000 -15.0000) '(6.0000 -15.0000) '(6.0000 -8.0000) '(0.0000 -8.0000) '(0.0000 -15.0000) "")
  (command "_pline" '(0.0000 -8.5000) '(6.0000 -8.5000) "")
  (command "_pline" '(3.0000 -8.0000) '(3.0000 -15.0000) "")
  (command "_pline" '(0.0000 15.0000) '(0.0000 8.0000) '(6.0000 8.0000) '(6.0000 15.0000) '(0.0000 15.0000) "")
  (command "_pline" '(0.0000 8.5000) '(6.0000 8.5000) "")
  (command "_pline" '(3.0000 8.0000) '(3.0000 15.0000) "")
)

(defun azt_rysuj_nakretke_m16 ()
  (command "_pline" '(7.0000 -13.8500) '(18.0000 -13.8500) "")
  (command "_pline" '(7.0000 -6.9250) '(18.0000 -6.9250) "")
  (command "_pline" '(7.0000 6.9250) '(18.0000 6.9250) "")
  (command "_pline" '(7.0000 13.8500) '(18.0000 13.8500) "")
  (command "_arc" '(7.0000 13.8500) "_C" '(12.4945 10.3875) '(7.0000 6.9250))
  (command "_arc" '(7.0000 6.9250) "_C" '(27.0153 0.5000) '(6.0000 0.0000))
  (command "_arc" '(6.0000 0.0000) "_C" '(27.0153 -0.5000) '(7.0000 -6.9250))
  (command "_arc" '(7.0000 -6.9250) "_C" '(12.4945 -10.3875) '(7.0000 -13.8500))
  (command "_arc" '(18.0000 -13.8500) "_C" '(12.5055 -10.3875) '(18.0000 -6.9250))
  (command "_arc" '(18.0000 -6.9250) "_C" '(-2.0153 -0.5000) '(19.0000 0.0000))
  (command "_arc" '(19.0000 0.0000) "_C" '(-2.0153 0.5000) '(18.0000 6.9250))
  (command "_arc" '(18.0000 6.9250) "_C" '(12.5055 10.3875) '(18.0000 13.8500))
  (command "_pline" '(6.0000 -10.3875) '(6.0000 10.3875) "")
  (command "_pline" '(19.0000 -10.3875) '(19.0000 10.3875) "")
)

(defun azt_rysuj_gwint_m16 ()
  (command "_pline" '(19.0000 -8.0000) '(38.0000 -8.0000) '(40.0000 -6.0000) '(40.0000 6.0000) '(38.0000 8.0000) '(19.0000 8.0000) "")
)

(defun azt_rysuj_niewidoczna_czesc_sruby_m16 ()
  (command "_pline" '(0.0000 -8.0000) '(2.0000 -6.0000) '(40.0000 -6.0000) "")
  (command "_pline" '(0.0000 8.0000) '(2.0000 6.0000) '(40.0000 6.0000) "")
  (command "_pline" '(2.0000 -8.0000) '(2.0000 8.0000) "")
  (command "_pline" '(38.0000 -8.0000) '(38.0000 8.0000) "")
)

(defun c:azt_sruba_widok_m16 ()
  (setq azt_aktualna_sruba_widok_typ "16")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m16)
  (setvar "CECOLOR" "126")
  (azt_rysuj_trzpien_m16)
  (setvar "CECOLOR" "127")
  (azt_rysuj_niewidoczna_czesc_sruby_m16)
  (setvar "CECOLOR" "128")
  (azt_rysuj_podkladki_m16)
  (azt_rysuj_nakretke_m16)
  (azt_rysuj_gwint_m16)
  (azt_wprowadz_skleszczenie_sruby)
  (azt_przywroc_ucs_sruby)
  (command "_ZOOM" "_SCALE" "0.0001X")
  (command "_layer" "_S" "0" "")
  (setvar "CECOLOR" "BYLAYER")
)

;#######################   SRUBA M16 - GWINT   #######################

(defun azt_rysuj_gwint_przekr_m16 ()
(command "_circle" '(0.0000 0.0000) '(15.0000 0.0000))
(command "_circle" '(0.0000 0.0000) '(11.0000 0.0000))
(command "_circle" '(0.0000 0.0000) '(8.0000 0.0000))
(command "_pline" '(0.0000 -13.8500) '(12.0000 -6.9250) '(12.0000 6.9250) '(0.0000 13.8500) '(-12.0000 6.9250) '(-12.0000 -6.9250) '(0.0000 -13.8500) "")
)

(defun azt_rysuj_osie_gwint_przekr_m16 ()
(command "_pline" '(0.0000 -19.3900) '(0.0000 19.3900) "")
(command "_pline" '(-16.8000 0.0000) '(16.8000 0.0000) "")
)

(defun c:azt_sruba_gwint_m16 ()
(setq azt_aktualna_sruba_gwint_typ "16")
(azt_punkt_wstawienia_sruby_przekr)
(command "_ZOOM" "_SCALE" "10000X")
(azt_ucs_wstawienia_sruby_przekr)
(command "_layer" "_S" "S_VIEW" "")
(azt_rysuj_gwint_przekr_m16)
(command "_layer" "_S" "S_GRIDS" "")
(azt_rysuj_osie_gwint_przekr_m16)
(azt_przywroc_ucs_sruby)
(command "_ZOOM" "_SCALE" "0.0001X")
(command "_layer" "_S" "0" "")
)


;#######################   SRUBA M16 - LEB   #######################

(defun azt_rysuj_leb_przekr_m16 ()
(command "_circle" '(0.0000 0.0000) '(11.0000 0.0000))
(command "_pline" '(0.0000 -13.8500) '(12.0000 -6.9250) '(12.0000 6.9250) '(0.0000 13.8500) '(-12.0000 6.9250) '(-12.0000 -6.9250) '(0.0000 -13.8500) "")
)

(defun azt_rysuj_osie_leb_przekr_m16 ()
(command "_pline" '(0.0000 -19.3900) '(0.0000 19.3900) "")
(command "_pline" '(-16.8000 0.0000) '(16.8000 0.0000) "")
)

(defun c:azt_sruba_leb_m16 ()
(setq azt_aktualna_sruba_leb_typ "16")
(azt_punkt_wstawienia_sruby_przekr)
(command "_ZOOM" "_SCALE" "10000X")
(azt_ucs_wstawienia_sruby_przekr)
(command "_layer" "_S" "S_VIEW" "")
(azt_rysuj_leb_przekr_m16)
(command "_layer" "_S" "S_GRIDS" "")
(azt_rysuj_osie_leb_przekr_m16)
(azt_przywroc_ucs_sruby)
(command "_ZOOM" "_SCALE" "0.0001X")
(command "_layer" "_S" "0" "")
)
;#######################   KONIEC SRUBY M16   #######################
;#######################   SRUBY - KONIEC  ##########################

;#######################   PROFILE - POCZATEK  #######################

(defun c:azt_wczytaj_baze_profili_stalowych ()
  (vl-cmdf "_.-insert" "C:\\AZT\\TEMPLATES\\SZABLON_PROFILI_STALOWYCH.dwg" '(0. 0. 0.) "" "" "")
  (vl-cmdf "_.erase" (entlast) "")
  (vl-cmdf "_.-purge" "Blocks" "SZABLON_PROFILI_STALOWYCH" "_N")
  (vl-cmdf "_.-purge" "Blocks" "AZT_PROFIL_WIDOK" "_N")
  (princ)
)

(defun c:azt_profil_widok_gora ()
  (setq azt_rodzina_profil_widok (getstring (strcat "\nWybierz rodzine profilu [HEA/HEB/UPE]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)
  
  (setq azt_typ_profil_widok (getstring (strcat "\nWybierz typ profilu [100/120/200]: <" azt_aktualny_typ_profil_widok ">")))
  (if (equal azt_typ_profil_widok "")
      (setq azt_typ_profil_widok azt_aktualny_typ_profil_widok)
      (princ)
  )
  (setq azt_aktualny_typ_profil_widok azt_typ_profil_widok)
  
  (setq azt_profil_widok_bok_wid (strcat "AZT_PROF_WID_G_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_bok_wid ()
  (setq azt_rodzina_profil_widok (getstring (strcat "\nWybierz rodzine profilu [HEA/HEB/UPE]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)
  
  (setq azt_typ_profil_widok (getstring (strcat "\nWybierz typ profilu [100/120/200]: <" azt_aktualny_typ_profil_widok ">")))
  (if (equal azt_typ_profil_widok "")
      (setq azt_typ_profil_widok azt_aktualny_typ_profil_widok)
      (princ)
  )
  (setq azt_aktualny_typ_profil_widok azt_typ_profil_widok)
  
  (setq azt_profil_widok_bok_wid (strcat "AZT_PROF_WID_B_W_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_bok_nwid ()
  (setq azt_rodzina_profil_widok (getstring (strcat "\nWybierz rodzine profilu [HEA/HEB/UPE]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)
  
  (setq azt_typ_profil_widok (getstring (strcat "\nWybierz typ profilu [100/120/200]: <" azt_aktualny_typ_profil_widok ">")))
  (if (equal azt_typ_profil_widok "")
      (setq azt_typ_profil_widok azt_aktualny_typ_profil_widok)
      (princ)
  )
  (setq azt_aktualny_typ_profil_widok azt_typ_profil_widok)
  
  (setq azt_profil_widok_bok_wid (strcat "AZT_PROF_WID_B_NW_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_odwroc_strone ()
  (repeat 100
  (setq azt_profil_widok_odwroc_strone_obiekt (entsel))
  (command "_mirror" azt_profil_widok_odwroc_strone_obiekt "" (cdr (assoc 10 (entget (car azt_profil_widok_odwroc_strone_obiekt)))) (cdr (assoc 11 (reverse (entget (car azt_profil_widok_odwroc_strone_obiekt))))) "_Y")
  ;(command "_mirror" (entlast) "" (cdr (assoc 10 (entget (entlast)))) (cdr (assoc 11 (reverse (entget (entlast))))) "_Y")
  )
  (princ)
)

;#######################   PROFILE - KONIEC  #######################

(azt_sruba_start)
(azt_profil_widok_start)
