(defun c:azt_sruba_widok ()
  (setq azt_sruba_widok_typ (getstring (strcat "\nPodaj srednice trzpienia sruby (MXX): <" azt_aktualna_sruba_widok_typ ">")))

 (if (equal azt_sruba_widok_typ "")
      (setq azt_sruba_widok_typ azt_aktualna_sruba_widok_typ)
      (princ "")
  )
  (if (equal azt_sruba_widok_typ "12")
      (setq azt_aktualna_sruba_widok_typ "12")
      (c:azt_sruba_widok_m12)
      (princ "")
  )
  (if (equal azt_sruba_widok_typ "16")
      (setq azt_aktualna_sruba_widok_typ "16")
      (c:azt_sruba_widok_m16)
      (princ "")
  )
)

(defun c:azt_sruba_gwint ()
  (setq azt_sruba_gwint_typ (getstring (strcat "\nPodaj srednice trzpienia sruby (MXX): <" azt_aktualna_sruba_gwint_typ ">")))

  (if (equal azt_sruba_gwint_typ "")
      (setq azt_sruba_gwint_typ azt_aktualna_sruba_gwint_typ)
      (princ "")
  )
  (if (equal azt_sruba_gwint_typ "12")
      (setq azt_aktualna_sruba_gwint_typ "12")
      (c:azt_sruba_gwint_m12)
      (princ "")
  )
  (if (equal azt_sruba_gwint_typ "16")
      (setq azt_aktualna_sruba_gwint_typ "16")
      (c:azt_sruba_gwint_m16)
      (princ "")
  )
)

(defun c:azt_sruba_leb ()
  (setq azt_sruba_leb_typ (getstring (strcat "\nPodaj srednice trzpienia sruby (MXX): <" azt_aktualna_sruba_leb_typ ">"))

  (if (equal azt_sruba_leb_typ "")
      (setq azt_sruba_leb_typ azt_aktualna_sruba_leb_typ)
      (princ "")
  )
  (if (equal azt_sruba_leb_typ "12")
      (setq azt_aktualna_sruba_leb_typ "12")
      (c:azt_sruba_leb_m12)
      (princ "")
  )
  (if (equal azt_sruba_leb_typ "16")
      (setq azt_aktualna_sruba_leb_typ "16")
      (c:azt_sruba_leb_m16)
      (princ "")
  )
)

;############  DANE WEJSCIOWE ###########

(defun azt_dane_wejsciowe_srub ()
(setq azt_aktualna_sruba_widok_typ "12")
(setq azt_aktualna_sruba_gwint_typ "12")
(setq azt_aktualna_sruba_leb_typ "12")
)
(azt_dane_wejsciowe_srub)
