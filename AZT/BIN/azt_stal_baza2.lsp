;#######################   DANE WEJSCIOWE ##########################

(defun azt_sruba_start ()
  (setq azt_aktualna_sruba_widok_typ "12")
  (setq azt_aktualna_sruba_gwint_typ "12")
  (setq azt_aktualna_sruba_leb_typ "12")
  (princ)
)

(defun azt_profil_widok_start ()
  (setq azt_aktualna_rodzina_profil_widok "HEA")
  (setq azt_aktualny_typ_profil_widok "100")
  (princ)
)

;#######################   SRUBY - POCZATEK  #######################

(defun azt_skleszczenie_sruby ()
  (setq azt_aktualne_skleszczenie_sruby (getstring (strcat "\nPodaj skleszczenie sruby: <" (rtos (distance azt_punkt1_skleszczenia_sruby azt_punkt2_skleszczenia_sruby) 2 0) ">")))
  (if (equal azt_aktualne_skleszczenie_sruby "")
      (setq azt_aktualne_skleszczenie_sruby (rtos (distance azt_punkt1_skleszczenia_sruby azt_punkt2_skleszczenia_sruby) 2 0))
      (princ)
  )
  (setq azt_aktualne_skleszczenie_sruby (atof azt_aktualne_skleszczenie_sruby))
)

(defun azt_punkty_skleszczenia_sruby ()
  (setq azt_punkt1_skleszczenia_sruby (getpoint "\nWskaz punkt wstawienia sruby: "))
  (setq azt_punkt2_skleszczenia_sruby (getpoint azt_punkt1_skleszczenia_sruby "\nWskaz kierunek wstawienia sruby: "))
)

(defun azt_punkt_wstawienia_sruby_przekr ()
  (setq azt_punkt1_wstawienia_sruby_przekr (getpoint "\nWskaz punkt wstawienia sruby: "))
  (setq azt_punkt2_wstawienia_sruby_przekr '(10.0 0.0 0.0))
)

(defun azt_wprowadz_skleszczenie_sruby ()
  (setq azt_selekcja_sruby_st_nwid (cadr (sssetfirst nil (ssget "_ALL" (list '(62 . 126))))))
  (setq azt_selekcja_sruby_nwid (cadr (sssetfirst nil (ssget "_ALL" (list '(62 . 127))))))
  (setq azt_selekcja_sruby_wid (cadr (sssetfirst nil (ssget "_ALL" (list '(62 . 128))))))
  (command "_move" azt_selekcja_sruby_nwid "" '(0.0 0.0 0.0) (list azt_aktualne_skleszczenie_sruby 0.0 0.0))
  (command "_move" azt_selekcja_sruby_wid "" '(0.0 0.0 0.0) (list azt_aktualne_skleszczenie_sruby 0.0 0.0))
  (command "_chprop" azt_selekcja_sruby_st_nwid "" "_C" "ByLayer" "")
  (command "_chprop" azt_selekcja_sruby_wid "" "_C" "ByLayer" "")
  (command "_chprop" azt_selekcja_sruby_nwid "" "_C" "ByLayer" "")
  (command "_.CHPROP" azt_selekcja_sruby_st_nwid "" "_LA" "S_VIEW HIDDEN" "")
  (command "_.CHPROP" azt_selekcja_sruby_wid "" "_LA" "S_VIEW" "")
  (command "_.CHPROP" azt_selekcja_sruby_nwid "" "_LA" "S_VIEW HIDDEN" "")
)

(defun azt_ucs_sruby ()
  (command "_UCS" azt_punkt1_skleszczenia_sruby (trans azt_punkt2_skleszczenia_sruby 0 1) "")
)

(defun azt_ucs_wstawienia_sruby_przekr ()
  (command "_UCS" azt_punkt1_wstawienia_sruby_przekr azt_punkt2_wstawienia_sruby_przekr "")
)

(defun azt_przywroc_ucs_sruby ()
  (command "_UCS" "_World")
  (princ)
)

(defun c:azt_sruba_widok ()
  (setq azt_sruba_widok_typ (getstring (strcat "\nPodaj srednice trzpienia sruby (MXX) [12/16/20/24/30]: <" azt_aktualna_sruba_widok_typ ">")))
  (if (equal azt_sruba_widok_typ "")
      (setq azt_sruba_widok_typ azt_aktualna_sruba_widok_typ)
      (princ)
  )
  (if (equal azt_sruba_widok_typ "12")
      (c:azt_sruba_widok_m12)
      (princ)
  )
  (if (equal azt_sruba_widok_typ "16")
      (c:azt_sruba_widok_m16)
      (princ)
  )
    (if (equal azt_sruba_widok_typ "20")
      (c:azt_sruba_widok_m20)
      (princ)
  )
  (if (equal azt_sruba_widok_typ "24")
      (c:azt_sruba_widok_m24)
      (princ)
  )
  (if (equal azt_sruba_widok_typ "30")
      (c:azt_sruba_widok_m30)
      (princ)
  )
  (princ)
)

(defun c:azt_sruba_gwint ()
(setq azt_sruba_gwint_typ (getstring (strcat "\nPodaj srednice trzpienia sruby (MXX) [12/16/20/24/30]: <" azt_aktualna_sruba_gwint_typ ">")))
  (if (equal azt_sruba_gwint_typ "")
      (setq azt_sruba_gwint_typ azt_aktualna_sruba_gwint_typ)
      (princ)
  )  
  (if (equal azt_sruba_gwint_typ "12")
      (c:azt_sruba_gwint_m12)
      (princ)
  )
  (if (equal azt_sruba_gwint_typ "16")
      (c:azt_sruba_gwint_m16)
      (princ)
  )
  (if (equal azt_sruba_gwint_typ "20")
      (c:azt_sruba_gwint_m20)
      (princ)
  )
  (if (equal azt_sruba_gwint_typ "24")
      (c:azt_sruba_gwint_m24)
      (princ)
  )
  (if (equal azt_sruba_gwint_typ "30")
      (c:azt_sruba_gwint_m30)
      (princ)
  )
  (princ)
)

(defun c:azt_sruba_leb ()
(setq azt_sruba_leb_typ (getstring (strcat "\nPodaj srednice trzpienia sruby (MXX) [12/16/20/24/30]: <" azt_aktualna_sruba_leb_typ ">")))
  (if (equal azt_sruba_leb_typ "")
      (setq azt_sruba_leb_typ azt_aktualna_sruba_leb_typ)
      (princ)
  )  
  (if (equal azt_sruba_leb_typ "12")
      (c:azt_sruba_leb_m12)
      (princ)
  )
  (if (equal azt_sruba_leb_typ "16")
      (c:azt_sruba_leb_m16)
      (princ)
  )
  (if (equal azt_sruba_leb_typ "20")
      (c:azt_sruba_leb_m20)
      (princ)
  )
  (if (equal azt_sruba_leb_typ "24")
      (c:azt_sruba_leb_m24)
      (princ)
  )
  (if (equal azt_sruba_leb_typ "30")
      (c:azt_sruba_leb_m30)
      (princ)
  )
  (princ)
)

;#######################   SRUBA M12   #######################
;#######################   SRUBA M12 - WIDOK   #######################

(defun azt_rysuj_leb_m12 ()
(command "_line" '(-8.00000000 8.21250000) '(-8.00000000 -8.21250000) "") (ssadd (entlast) azt_sruba_scalenie)
(command "_line" '(-8.00000000 0.00000000) '(-8.00000000 8.21250000) "") (ssadd (entlast) azt_sruba_scalenie)
(command "_arc" "_C" '(4.75031250 -0.50000000) "@12.76011242<178" "_A" "25") (ssadd (entlast) azt_sruba_scalenie)
(command "_line" '(-8.00000000 -8.21250000) '(-8.00000000 0.00000000) "") (ssadd (entlast) azt_sruba_scalenie)
(command "_arc" "_C" '(4.75031250 0.50000000) "@12.76011242<157" "_A" "25") (ssadd (entlast) azt_sruba_scalenie)
(command "_line" '(0.00000000 6.00000000) '(0.00000000 10.95000000) "") (ssadd (entlast) azt_sruba_scalenie)
(command "_line" '(0.00000000 0.00000000) '(0.00000000 6.00000000) "") (ssadd (entlast) azt_sruba_scalenie)
(command "_arc" "_C" '(-3.75304687 8.21250000) "@4.24695313<140" "_A" "80") (ssadd (entlast) azt_sruba_scalenie)
(command "_line" '(0.00000000 10.95000000) '(-7.00000000 10.95000000) "") (ssadd (entlast) azt_sruba_scalenie)
(command "_line" '(0.00000000 -5.47500000) '(-7.00000000 -5.47500000) "") (ssadd (entlast) azt_sruba_scalenie)
(command "_line" '(0.00000000 5.47500000) '(0.00000000 -5.47500000) "") (ssadd (entlast) azt_sruba_scalenie)
(command "_line" '(0.00000000 -5.47500000) '(0.00000000 -6.00000000) "") (ssadd (entlast) azt_sruba_scalenie)
(command "_line" '(-7.00000000 -5.47500000) '(0.00000000 -5.47500000) "") (ssadd (entlast) azt_sruba_scalenie)
(command "_line" '(-7.00000000 5.47500000) '(0.00000000 5.47500000) "") (ssadd (entlast) azt_sruba_scalenie)
(command "_line" '(-7.00000000 -10.95000000) '(0.00000000 -10.95000000) "") (ssadd (entlast) azt_sruba_scalenie)
(command "_arc" "_C" '(-3.75304688 -8.21250000) "@4.24695312<140" "_A" "80") (ssadd (entlast) azt_sruba_scalenie)
(command "_line" '(0.00000000 5.47500000) '(-7.00000000 5.47500000) "") (ssadd (entlast) azt_sruba_scalenie)
(command "_line" '(0.00000000 -10.95000000) '(0.00000000 5.47500000) "") (ssadd (entlast) azt_sruba_scalenie)
)

(defun azt_rysuj_trzpien_m12 ()
(command "_pline" '(0.0 6.0) (list azt_aktualne_skleszczenie_sruby 6.0 ) "") (ssadd (entlast) azt_sruba_scalenie)
(command "_pline" '(0.0 -6.0) (list azt_aktualne_skleszczenie_sruby -6.0 ) "") (ssadd (entlast) azt_sruba_scalenie)
)

(defun azt_rysuj_podkladki_m12 ()
(command "_line" '(2.50000000 -12.00000000) '(2.50000000 -6.50000000) "") (ssadd (entlast) azt_sruba_scalenie)
(command "_line" '(0.00000000 -12.00000000) '(2.50000000 -12.00000000) "") (ssadd (entlast) azt_sruba_scalenie)
(command "_line" '(0.00000000 -6.00000000) '(0.00000000 -12.00000000) "") (ssadd (entlast) azt_sruba_scalenie)
(command "_line" '(5.00000000 -12.00000000) '(5.00000000 -6.50000000) "") (ssadd (entlast) azt_sruba_scalenie)
(command "_line" '(2.50000000 -12.00000000) '(5.00000000 -12.00000000) "") (ssadd (entlast) azt_sruba_scalenie)
(command "_line" '(2.50000000 -6.50000000) '(2.50000000 -12.00000000) "") (ssadd (entlast) azt_sruba_scalenie)
(command "_line" '(2.50000000 -6.50000000) '(2.50000000 -6.00000000) "") (ssadd (entlast) azt_sruba_scalenie)
(command "_line" '(5.00000000 -6.50000000) '(2.50000000 -6.50000000) "") (ssadd (entlast) azt_sruba_scalenie)
(command "_line" '(5.00000000 -6.00000000) '(5.00000000 -6.50000000) "") (ssadd (entlast) azt_sruba_scalenie)
(command "_line" '(0.00000000 -6.50000000) '(0.00000000 -6.00000000) "") (ssadd (entlast) azt_sruba_scalenie)
(command "_line" '(2.50000000 -6.50000000) '(0.00000000 -6.50000000) "") (ssadd (entlast) azt_sruba_scalenie)
(command "_line" '(2.50000000 -6.00000000) '(2.50000000 -6.50000000) "") (ssadd (entlast) azt_sruba_scalenie)
(command "_line" '(2.50000000 6.50000000) '(5.00000000 6.50000000) "") (ssadd (entlast) azt_sruba_scalenie)
(command "_line" '(2.50000000 12.00000000) '(2.50000000 6.50000000) "") (ssadd (entlast) azt_sruba_scalenie)
(command "_line" '(2.50000000 6.00000000) '(2.50000000 12.00000000) "") (ssadd (entlast) azt_sruba_scalenie)
(command "_line" '(0.00000000 -6.00000000) '(5.00000000 -6.00000000) "") (ssadd (entlast) azt_sruba_scalenie)
(command "_line" '(0.00000000 6.00000000) '(5.00000000 6.00000000) "") (ssadd (entlast) azt_sruba_scalenie)
(command "_line" '(5.00000000 6.50000000) '(5.00000000 6.00000000) "") (ssadd (entlast) azt_sruba_scalenie)
(command "_line" '(0.00000000 12.00000000) '(0.00000000 6.00000000) "") (ssadd (entlast) azt_sruba_scalenie)
(command "_line" '(5.00000000 12.00000000) '(0.00000000 12.00000000) "") (ssadd (entlast) azt_sruba_scalenie)
(command "_line" '(5.00000000 6.50000000) '(5.00000000 12.00000000) "") (ssadd (entlast) azt_sruba_scalenie)
(command "_line" '(2.50000000 6.50000000) '(2.50000000 6.00000000) "") (ssadd (entlast) azt_sruba_scalenie)
(command "_line" '(0.00000000 6.50000000) '(2.50000000 6.50000000) "") (ssadd (entlast) azt_sruba_scalenie)
(command "_line" '(0.00000000 6.00000000) '(0.00000000 6.50000000) "") (ssadd (entlast) azt_sruba_scalenie)
)

(defun azt_rysuj_nakretke_m12 ()
(command "_arc" "_C" '(9.24695313 8.21250000) "@4.24695313<140" "_A" "80") (ssadd (entlast) azt_sruba_scalenie)
(command "_line" '(14.00000000 5.47500000) '(6.00000000 5.47500000) "") (ssadd (entlast) azt_sruba_scalenie)
(command "_line" '(6.00000000 5.47500000) '(14.00000000 5.47500000) "") (ssadd (entlast) azt_sruba_scalenie)
(command "_arc" "_C" '(2.24968750 0.50000000) "@12.76011242<358" "_A" "25") (ssadd (entlast) azt_sruba_scalenie)
(command "_arc" "_C" '(10.75304687 8.21250000) "@4.24695313<320" "_A" "80") (ssadd (entlast) azt_sruba_scalenie)
(command "_line" '(6.00000000 10.95000000) '(14.00000000 10.95000000) "") (ssadd (entlast) azt_sruba_scalenie)
(command "_line" '(5.00000000 0.00000000) '(5.00000000 -8.21250000) "") (ssadd (entlast) azt_sruba_scalenie)
(command "_line" '(5.00000000 -6.50000000) '(5.00000000 0.00000000) "") (ssadd (entlast) azt_sruba_scalenie)
(command "_line" '(5.00000000 -6.00000000) '(5.00000000 -6.50000000) "") (ssadd (entlast) azt_sruba_scalenie)
(command "_arc" "_C" '(17.75031250 0.50000000) "@12.76011242<157" "_A" "25") (ssadd (entlast) azt_sruba_scalenie)
(command "_line" '(5.00000000 8.21250000) '(5.00000000 0.00000000) "") (ssadd (entlast) azt_sruba_scalenie)
(command "_line" '(5.00000000 -8.21250000) '(5.00000000 8.21250000) "") (ssadd (entlast) azt_sruba_scalenie)
(command "_line" '(15.00000000 0.00000000) '(15.00000000 8.21250000) "") (ssadd (entlast) azt_sruba_scalenie)
(command "_line" '(14.00000000 -5.47500000) '(6.00000000 -5.47500000) "") (ssadd (entlast) azt_sruba_scalenie)
(command "_line" '(6.00000000 -5.47500000) '(14.00000000 -5.47500000) "") (ssadd (entlast) azt_sruba_scalenie)
(command "_arc" "_C" '(9.24695312 -8.21250000) "@4.24695312<140" "_A" "80") (ssadd (entlast) azt_sruba_scalenie)
(command "_line" '(5.00000000 6.50000000) '(5.00000000 6.00000000) "") (ssadd (entlast) azt_sruba_scalenie)
(command "_line" '(5.00000000 0.00000000) '(5.00000000 6.50000000) "") (ssadd (entlast) azt_sruba_scalenie)
(command "_arc" "_C" '(17.75031250 -0.50000000) "@12.76011242<178" "_A" "25") (ssadd (entlast) azt_sruba_scalenie)
(command "_line" '(15.00000000 -8.21250000) '(15.00000000 0.00000000) "") (ssadd (entlast) azt_sruba_scalenie)
(command "_line" '(15.00000000 -6.00000000) '(15.00000000 -8.21250000) "") (ssadd (entlast) azt_sruba_scalenie)
(command "_line" '(15.00000000 8.21250000) '(15.00000000 6.00000000) "") (ssadd (entlast) azt_sruba_scalenie)
(command "_line" '(14.00000000 -10.95000000) '(6.00000000 -10.95000000) "") (ssadd (entlast) azt_sruba_scalenie)
(command "_arc" "_C" '(10.75304688 -8.21250000) "@4.24695312<320" "_A" "80") (ssadd (entlast) azt_sruba_scalenie)
(command "_arc" "_C" '(2.24968750 -0.50000000) "@12.76011242<337" "_A" "25") (ssadd (entlast) azt_sruba_scalenie)
)

(defun azt_rysuj_gwint_m12 ()
(command "_line" '(33.00000000 6.00000000) '(35.00000000 4.00000000) "") (ssadd (entlast) azt_sruba_scalenie)
(command "_line" '(15.00000000 6.00000000) '(33.00000000 6.00000000) "") (ssadd (entlast) azt_sruba_scalenie)
(command "_line" '(35.00000000 4.00000000) '(35.00000000 -4.00000000) "") (ssadd (entlast) azt_sruba_scalenie)
(command "_line" '(33.00000000 -6.00000000) '(15.00000000 -6.00000000) "") (ssadd (entlast) azt_sruba_scalenie)
(command "_line" '(35.00000000 -4.00000000) '(33.00000000 -6.00000000) "") (ssadd (entlast) azt_sruba_scalenie)
)

(defun azt_rysuj_niewidoczna_czesc_sruby_m12 ()
(command "_line" '(5.00000000 -4.00000000) '(3.00000000 -6.00000000) "") (ssadd (entlast) azt_sruba_scalenie)
(command "_line" '(3.00000000 -6.00000000) '(5.00000000 -4.00000000) "") (ssadd (entlast) azt_sruba_scalenie)
(command "_line" '(5.00000000 -4.00000000) '(5.00000000 -6.00000000) "") (ssadd (entlast) azt_sruba_scalenie)
(command "_line" '(5.00000000 4.00000000) '(5.00000000 -4.00000000) "") (ssadd (entlast) azt_sruba_scalenie)
(command "_line" '(3.00000000 6.00000000) '(5.00000000 4.00000000) "") (ssadd (entlast) azt_sruba_scalenie)
(command "_line" '(5.00000000 4.00000000) '(5.00000000 6.00000000) "") (ssadd (entlast) azt_sruba_scalenie)
(command "_line" '(5.00000000 6.00000000) '(5.00000000 4.00000000) "") (ssadd (entlast) azt_sruba_scalenie)
(command "_line" '(5.00000000 -6.00000000) '(5.00000000 -4.00000000) "") (ssadd (entlast) azt_sruba_scalenie)
(command "_line" '(33.00000000 6.00000000) '(33.00000000 4.00000000) "") (ssadd (entlast) azt_sruba_scalenie)
(command "_line" '(33.00000000 4.00000000) '(35.00000000 4.00000000) "") (ssadd (entlast) azt_sruba_scalenie)
(command "_line" '(35.00000000 4.00000000) '(5.00000000 4.00000000) "") (ssadd (entlast) azt_sruba_scalenie)
(command "_line" '(33.00000000 -6.00000000) '(33.00000000 6.00000000) "") (ssadd (entlast) azt_sruba_scalenie)
(command "_line" '(5.00000000 -4.00000000) '(35.00000000 -4.00000000) "") (ssadd (entlast) azt_sruba_scalenie)
(command "_line" '(35.00000000 -4.00000000) '(33.00000000 -4.00000000) "") (ssadd (entlast) azt_sruba_scalenie)
(command "_line" '(33.00000000 -4.00000000) '(33.00000000 -6.00000000) "") (ssadd (entlast) azt_sruba_scalenie)
)

(defun c:azt_sruba_widok_m12 ()
  (setq azt_sruba_scalenie (ssadd))
  (setq azt_aktualna_sruba_widok_typ "12")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m12)
  (setvar "CECOLOR" "126")
  (azt_rysuj_trzpien_m12)
  (setvar "CECOLOR" "127")
  (azt_rysuj_niewidoczna_czesc_sruby_m12)
  (setvar "CECOLOR" "128")
  (azt_rysuj_podkladki_m12)
  (azt_rysuj_nakretke_m12)
  (azt_rysuj_gwint_m12)
  (azt_wprowadz_skleszczenie_sruby)
  (azt_przywroc_ucs_sruby)
  (command "_ZOOM" "_SCALE" "0.0001X")
  (command "_layer" "_S" "0" "")
  (setvar "CECOLOR" "BYLAYER")
  (command "_group" "_C" "*" "" azt_sruba_scalenie "")
  (setq azt_sruba_scalenie (ssadd))
)

;#######################   SRUBA M12 - GWINT   #######################

(defun azt_rysuj_gwint_przekr_m12 ()
(command "_line" '(-9.50000000 -5.47500000) '(0.00000000 -10.95000000) "") (ssadd (entlast) azt_sruba_scalenie)
(command "_line" '(0.00000000 -10.95000000) '(9.50000000 -5.47500000) "") (ssadd (entlast) azt_sruba_scalenie)
(command "_line" '(0.00000000 10.95000000) '(-9.50000000 5.47500000) "") (ssadd (entlast) azt_sruba_scalenie)
(command "_line" '(-9.50000000 5.47500000) '(-9.50000000 -5.47500000) "") (ssadd (entlast) azt_sruba_scalenie)
(command "_line" '(9.50000000 -5.47500000) '(9.50000000 5.47500000) "") (ssadd (entlast) azt_sruba_scalenie)
(command "_circle" '(0.00000000 0.00000000) "6.00000000") (ssadd (entlast) azt_sruba_scalenie)
(command "_circle" '(0.00000000 0.00000000) "12.00000000") (ssadd (entlast) azt_sruba_scalenie)
(command "_line" '(9.50000000 5.47500000) '(0.00000000 10.95000000) "") (ssadd (entlast) azt_sruba_scalenie)
(command "_circle" '(0.00000000 0.00000000) "8.50000000") (ssadd (entlast) azt_sruba_scalenie)
)

(defun azt_rysuj_osie_gwint_przekr_m12 ()
(command "_line" '(0.00000000 0.00000000) '(19.00000000 0.00000000) "") (ssadd (entlast) azt_sruba_scalenie)
(command "_line" '(-19.00000000 0.00000000) '(0.00000000 0.00000000) "") (ssadd (entlast) azt_sruba_scalenie)
(command "_line" '(0.00000000 0.00000000) '(0.00000000 -21.90000000) "") (ssadd (entlast) azt_sruba_scalenie)
(command "_line" '(0.00000000 21.90000000) '(0.00000000 0.00000000) "") (ssadd (entlast) azt_sruba_scalenie)
)

(defun c:azt_sruba_gwint_m12 ()
(setq azt_sruba_scalenie (ssadd))
(setq azt_aktualna_sruba_gwint_typ "12")
(azt_punkt_wstawienia_sruby_przekr)
(command "_ZOOM" "_SCALE" "10000X")
(azt_ucs_wstawienia_sruby_przekr)
(command "_layer" "_S" "S_VIEW" "")
(azt_rysuj_gwint_przekr_m12)
(command "_layer" "_S" "S_GRIDS" "")
(azt_rysuj_osie_gwint_przekr_m12)
(azt_przywroc_ucs_sruby)
(command "_ZOOM" "_SCALE" "0.0001X")
(command "_layer" "_S" "0" "")
(command "_group" "_C" "*" "" azt_sruba_scalenie "")
(setq azt_sruba_scalenie (ssadd))
)

;#######################   SRUBA M12 - LEB   #######################

(defun azt_rysuj_leb_przekr_m12 ()
(command "_line" '(-9.50000000 -5.47500000) '(0.00000000 -10.95000000) "") (ssadd (entlast) azt_sruba_scalenie)
(command "_line" '(-9.50000000 5.47500000) '(-9.50000000 -5.47500000) "") (ssadd (entlast) azt_sruba_scalenie)
(command "_line" '(0.00000000 10.95000000) '(-9.50000000 5.47500000) "") (ssadd (entlast) azt_sruba_scalenie)
(command "_line" '(0.00000000 -10.95000000) '(9.50000000 -5.47500000) "") (ssadd (entlast) azt_sruba_scalenie)
(command "_circle" '(0.00000000 0.00000000) "8.50000000") (ssadd (entlast) azt_sruba_scalenie)
(command "_line" '(9.50000000 5.47500000) '(0.00000000 10.95000000) "") (ssadd (entlast) azt_sruba_scalenie)
(command "_line" '(9.50000000 -5.47500000) '(9.50000000 5.47500000) "") (ssadd (entlast) azt_sruba_scalenie)
)

(defun azt_rysuj_osie_leb_przekr_m12 ()
(command "_line" '(0.00000000 0.00000000) '(19.00000000 0.00000000) "") (ssadd (entlast) azt_sruba_scalenie)
(command "_line" '(-19.00000000 0.00000000) '(0.00000000 0.00000000) "") (ssadd (entlast) azt_sruba_scalenie)
(command "_line" '(0.00000000 0.00000000) '(0.00000000 -21.90000000) "") (ssadd (entlast) azt_sruba_scalenie)
(command "_line" '(0.00000000 21.90000000) '(0.00000000 0.00000000) "") (ssadd (entlast) azt_sruba_scalenie)
)

(defun c:azt_sruba_leb_m12 ()
(setq azt_sruba_scalenie (ssadd))
(setq azt_aktualna_sruba_leb_typ "12")
(azt_punkt_wstawienia_sruby_przekr)
(command "_ZOOM" "_SCALE" "10000X")
(azt_ucs_wstawienia_sruby_przekr)
(command "_layer" "_S" "S_VIEW" "")
(azt_rysuj_leb_przekr_m12)
(command "_layer" "_S" "S_GRIDS" "")
(azt_rysuj_osie_leb_przekr_m12)
(azt_przywroc_ucs_sruby)
(command "_ZOOM" "_SCALE" "0.0001X")
(command "_layer" "_S" "0" "")
(command "_group" "_C" "*" "" azt_sruba_scalenie "")
(setq azt_sruba_scalenie (ssadd))
)

;#######################   KONIEC SRUBY M12   #######################

;#######################   SRUBA M16   #######################
;#######################   SRUBA M16 - WIDOK   #######################

(defun azt_rysuj_leb_m16 ()
(command "_line" '(-10.00000000 10.38750000) '(-10.00000000 -10.38750000) "") (ssadd (entlast) azt_sruba_scalenie)
(command "_line" '(-10.00000000 0.00000000) '(-10.00000000 10.38750000) "") (ssadd (entlast) azt_sruba_scalenie)
(command "_arc" "_C" '(11.01531250 -0.50000000) "@21.02125970<179" "_A" "19") (ssadd (entlast) azt_sruba_scalenie)
(command "_line" '(-10.00000000 -10.38750000) '(-10.00000000 0.00000000) "") (ssadd (entlast) azt_sruba_scalenie)
(command "_arc" "_C" '(11.01531250 0.50000000) "@21.02125970<162" "_A" "19") (ssadd (entlast) azt_sruba_scalenie)
(command "_line" '(0.00000000 8.00000000) '(0.00000000 13.85000000) "") (ssadd (entlast) azt_sruba_scalenie)
(command "_line" '(0.00000000 0.00000000) '(0.00000000 8.00000000) "") (ssadd (entlast) azt_sruba_scalenie)
(command "_arc" "_C" '(-3.50554687 10.38750000) "@6.49445313<148" "_A" "64") (ssadd (entlast) azt_sruba_scalenie)
(command "_line" '(0.00000000 13.85000000) '(-9.00000000 13.85000000) "") (ssadd (entlast) azt_sruba_scalenie)
(command "_line" '(0.00000000 -6.92500000) '(-9.00000000 -6.92500000) "") (ssadd (entlast) azt_sruba_scalenie)
(command "_line" '(0.00000000 6.92500000) '(0.00000000 -6.92500000) "") (ssadd (entlast) azt_sruba_scalenie)
(command "_line" '(0.00000000 -6.92500000) '(0.00000000 -8.00000000) "") (ssadd (entlast) azt_sruba_scalenie)
(command "_line" '(-9.00000000 -6.92500000) '(0.00000000 -6.92500000) "") (ssadd (entlast) azt_sruba_scalenie)
(command "_line" '(-9.00000000 6.92500000) '(0.00000000 6.92500000) "") (ssadd (entlast) azt_sruba_scalenie)
(command "_line" '(-9.00000000 -13.85000000) '(0.00000000 -13.85000000) "") (ssadd (entlast) azt_sruba_scalenie)
(command "_arc" "_C" '(-3.50554687 -10.38750000) "@6.49445313<148" "_A" "64") (ssadd (entlast) azt_sruba_scalenie)
(command "_line" '(0.00000000 6.92500000) '(-9.00000000 6.92500000) "") (ssadd (entlast) azt_sruba_scalenie)
(command "_line" '(0.00000000 -13.85000000) '(0.00000000 6.92500000) "") (ssadd (entlast) azt_sruba_scalenie)
)

(defun azt_rysuj_trzpien_m16 ()
(command "_pline" '(0.0 8.0) (list azt_aktualne_skleszczenie_sruby 8.0 ) "") (ssadd (entlast) azt_sruba_scalenie)
(command "_pline" '(0.0 -8.0) (list azt_aktualne_skleszczenie_sruby -8.0 ) "") (ssadd (entlast) azt_sruba_scalenie)
)

(defun azt_rysuj_podkladki_m16 ()
(command "_line" '(3.00000000 -15.00000000) '(3.00000000 -8.50000000) "") (ssadd (entlast) azt_sruba_scalenie)
(command "_line" '(0.00000000 -15.00000000) '(3.00000000 -15.00000000) "") (ssadd (entlast) azt_sruba_scalenie)
(command "_line" '(0.00000000 -8.00000000) '(0.00000000 -15.00000000) "") (ssadd (entlast) azt_sruba_scalenie)
(command "_line" '(6.00000000 -15.00000000) '(6.00000000 -8.50000000) "") (ssadd (entlast) azt_sruba_scalenie)
(command "_line" '(3.00000000 -15.00000000) '(6.00000000 -15.00000000) "") (ssadd (entlast) azt_sruba_scalenie)
(command "_line" '(3.00000000 -8.50000000) '(3.00000000 -15.00000000) "") (ssadd (entlast) azt_sruba_scalenie)
(command "_line" '(3.00000000 -8.50000000) '(3.00000000 -8.00000000) "") (ssadd (entlast) azt_sruba_scalenie)
(command "_line" '(6.00000000 -8.50000000) '(3.00000000 -8.50000000) "") (ssadd (entlast) azt_sruba_scalenie)
(command "_line" '(6.00000000 -8.00000000) '(6.00000000 -8.50000000) "") (ssadd (entlast) azt_sruba_scalenie)
(command "_line" '(0.00000000 -8.50000000) '(0.00000000 -8.00000000) "") (ssadd (entlast) azt_sruba_scalenie)
(command "_line" '(3.00000000 -8.50000000) '(0.00000000 -8.50000000) "") (ssadd (entlast) azt_sruba_scalenie)
(command "_line" '(3.00000000 -8.00000000) '(3.00000000 -8.50000000) "") (ssadd (entlast) azt_sruba_scalenie)
(command "_line" '(3.00000000 8.50000000) '(6.00000000 8.50000000) "") (ssadd (entlast) azt_sruba_scalenie)
(command "_line" '(3.00000000 15.00000000) '(3.00000000 8.50000000) "") (ssadd (entlast) azt_sruba_scalenie)
(command "_line" '(3.00000000 8.00000000) '(3.00000000 15.00000000) "") (ssadd (entlast) azt_sruba_scalenie)
(command "_line" '(0.00000000 -8.00000000) '(6.00000000 -8.00000000) "") (ssadd (entlast) azt_sruba_scalenie)
(command "_line" '(0.00000000 8.00000000) '(6.00000000 8.00000000) "") (ssadd (entlast) azt_sruba_scalenie)
(command "_line" '(6.00000000 8.50000000) '(6.00000000 8.00000000) "") (ssadd (entlast) azt_sruba_scalenie)
(command "_line" '(0.00000000 15.00000000) '(0.00000000 8.00000000) "") (ssadd (entlast) azt_sruba_scalenie)
(command "_line" '(6.00000000 15.00000000) '(0.00000000 15.00000000) "") (ssadd (entlast) azt_sruba_scalenie)
(command "_line" '(6.00000000 8.50000000) '(6.00000000 15.00000000) "") (ssadd (entlast) azt_sruba_scalenie)
(command "_line" '(3.00000000 8.50000000) '(3.00000000 8.00000000) "") (ssadd (entlast) azt_sruba_scalenie)
(command "_line" '(0.00000000 8.50000000) '(3.00000000 8.50000000) "") (ssadd (entlast) azt_sruba_scalenie)
(command "_line" '(0.00000000 8.00000000) '(0.00000000 8.50000000) "") (ssadd (entlast) azt_sruba_scalenie)
)

(defun azt_rysuj_nakretke_m16 ()
(command "_arc" "_C" '(12.49445313 10.38750000) "@6.49445313<148" "_A" "64") (ssadd (entlast) azt_sruba_scalenie)
(command "_line" '(18.00000000 6.92500000) '(7.00000000 6.92500000) "") (ssadd (entlast) azt_sruba_scalenie)
(command "_line" '(7.00000000 6.92500000) '(18.00000000 6.92500000) "") (ssadd (entlast) azt_sruba_scalenie)
(command "_arc" "_C" '(-2.01531250 0.50000000) "@21.02125970<359" "_A" "19") (ssadd (entlast) azt_sruba_scalenie)
(command "_arc" "_C" '(12.50554687 10.38750000) "@6.49445313<328" "_A" "64") (ssadd (entlast) azt_sruba_scalenie)
(command "_line" '(7.00000000 13.85000000) '(18.00000000 13.85000000) "") (ssadd (entlast) azt_sruba_scalenie)
(command "_line" '(6.00000000 0.00000000) '(6.00000000 -10.38750000) "") (ssadd (entlast) azt_sruba_scalenie)
(command "_line" '(6.00000000 -8.50000000) '(6.00000000 0.00000000) "") (ssadd (entlast) azt_sruba_scalenie)
(command "_line" '(6.00000000 -8.00000000) '(6.00000000 -8.50000000) "") (ssadd (entlast) azt_sruba_scalenie)
(command "_arc" "_C" '(27.01531250 0.50000000) "@21.02125970<162" "_A" "19") (ssadd (entlast) azt_sruba_scalenie)
(command "_line" '(6.00000000 10.38750000) '(6.00000000 0.00000000) "") (ssadd (entlast) azt_sruba_scalenie)
(command "_line" '(6.00000000 -10.38750000) '(6.00000000 10.38750000) "") (ssadd (entlast) azt_sruba_scalenie)
(command "_line" '(19.00000000 0.00000000) '(19.00000000 10.38750000) "") (ssadd (entlast) azt_sruba_scalenie)
(command "_line" '(18.00000000 -6.92500000) '(7.00000000 -6.92500000) "") (ssadd (entlast) azt_sruba_scalenie)
(command "_line" '(7.00000000 -6.92500000) '(18.00000000 -6.92500000) "") (ssadd (entlast) azt_sruba_scalenie)
(command "_arc" "_C" '(12.49445313 -10.38750000) "@6.49445313<148" "_A" "64") (ssadd (entlast) azt_sruba_scalenie)
(command "_line" '(6.00000000 8.50000000) '(6.00000000 8.00000000) "") (ssadd (entlast) azt_sruba_scalenie)
(command "_line" '(6.00000000 0.00000000) '(6.00000000 8.50000000) "") (ssadd (entlast) azt_sruba_scalenie)
(command "_arc" "_C" '(27.01531250 -0.50000000) "@21.02125970<179" "_A" "19") (ssadd (entlast) azt_sruba_scalenie)
(command "_line" '(19.00000000 -10.38750000) '(19.00000000 0.00000000) "") (ssadd (entlast) azt_sruba_scalenie)
(command "_line" '(19.00000000 -8.00000000) '(19.00000000 -10.38750000) "") (ssadd (entlast) azt_sruba_scalenie)
(command "_line" '(19.00000000 10.38750000) '(19.00000000 8.00000000) "") (ssadd (entlast) azt_sruba_scalenie)
(command "_line" '(18.00000000 -13.85000000) '(7.00000000 -13.85000000) "") (ssadd (entlast) azt_sruba_scalenie)
(command "_arc" "_C" '(12.50554687 -10.38750000) "@6.49445313<328" "_A" "64") (ssadd (entlast) azt_sruba_scalenie)
(command "_arc" "_C" '(-2.01531250 -0.50000000) "@21.02125970<342" "_A" "19") (ssadd (entlast) azt_sruba_scalenie)
)

(defun azt_rysuj_gwint_m16 ()
(command "_line" '(38.00000000 8.00000000) '(40.00000000 6.00000000) "") (ssadd (entlast) azt_sruba_scalenie)
(command "_line" '(19.00000000 8.00000000) '(38.00000000 8.00000000) "") (ssadd (entlast) azt_sruba_scalenie)
(command "_line" '(40.00000000 6.00000000) '(40.00000000 -6.00000000) "") (ssadd (entlast) azt_sruba_scalenie)
(command "_line" '(38.00000000 -8.00000000) '(19.00000000 -8.00000000) "") (ssadd (entlast) azt_sruba_scalenie)
(command "_line" '(40.00000000 -6.00000000) '(38.00000000 -8.00000000) "") (ssadd (entlast) azt_sruba_scalenie)
)

(defun azt_rysuj_niewidoczna_czesc_sruby_m16 ()
(command "_line" '(2.00000000 -6.00000000) '(0.00000000 -8.00000000) "") (ssadd (entlast) azt_sruba_scalenie)
(command "_line" '(0.00000000 -8.00000000) '(2.00000000 -6.00000000) "") (ssadd (entlast) azt_sruba_scalenie)
(command "_line" '(2.00000000 -6.00000000) '(2.00000000 -8.00000000) "") (ssadd (entlast) azt_sruba_scalenie)
(command "_line" '(2.00000000 6.00000000) '(2.00000000 -6.00000000) "") (ssadd (entlast) azt_sruba_scalenie)
(command "_line" '(0.00000000 8.00000000) '(2.00000000 6.00000000) "") (ssadd (entlast) azt_sruba_scalenie)
(command "_line" '(2.00000000 6.00000000) '(2.00000000 8.00000000) "") (ssadd (entlast) azt_sruba_scalenie)
(command "_line" '(2.00000000 8.00000000) '(2.00000000 6.00000000) "") (ssadd (entlast) azt_sruba_scalenie)
(command "_line" '(2.00000000 -8.00000000) '(2.00000000 -6.00000000) "") (ssadd (entlast) azt_sruba_scalenie)
(command "_line" '(38.00000000 8.00000000) '(38.00000000 6.00000000) "") (ssadd (entlast) azt_sruba_scalenie)
(command "_line" '(38.00000000 6.00000000) '(40.00000000 6.00000000) "") (ssadd (entlast) azt_sruba_scalenie)
(command "_line" '(40.00000000 6.00000000) '(2.00000000 6.00000000) "") (ssadd (entlast) azt_sruba_scalenie)
(command "_line" '(38.00000000 -8.00000000) '(38.00000000 8.00000000) "") (ssadd (entlast) azt_sruba_scalenie)
(command "_line" '(2.00000000 -6.00000000) '(40.00000000 -6.00000000) "") (ssadd (entlast) azt_sruba_scalenie)
(command "_line" '(40.00000000 -6.00000000) '(38.00000000 -6.00000000) "") (ssadd (entlast) azt_sruba_scalenie)
(command "_line" '(38.00000000 -6.00000000) '(38.00000000 -8.00000000) "") (ssadd (entlast) azt_sruba_scalenie)
)

(defun c:azt_sruba_widok_m16 ()
  (setq azt_sruba_scalenie (ssadd))
  (setq azt_aktualna_sruba_widok_typ "16")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m16)
  (setvar "CECOLOR" "126")
  (azt_rysuj_trzpien_m16)
  (setvar "CECOLOR" "127")
  (azt_rysuj_niewidoczna_czesc_sruby_m16)
  (setvar "CECOLOR" "128")
  (azt_rysuj_podkladki_m16)
  (azt_rysuj_nakretke_m16)
  (azt_rysuj_gwint_m16)
  (azt_wprowadz_skleszczenie_sruby)
  (azt_przywroc_ucs_sruby)
  (command "_ZOOM" "_SCALE" "0.0001X")
  (command "_layer" "_S" "0" "")
  (setvar "CECOLOR" "BYLAYER")
  (command "_group" "_C" "*" "" azt_sruba_scalenie "")
  (setq azt_sruba_scalenie (ssadd))
)

;#######################   SRUBA M16 - GWINT   #######################

(defun azt_rysuj_gwint_przekr_m16 ()
(command "_line" '(-12.00000000 -6.92500000) '(0.00000000 -13.85000000) "") (ssadd (entlast) azt_sruba_scalenie)
(command "_line" '(0.00000000 -13.85000000) '(12.00000000 -6.92500000) "") (ssadd (entlast) azt_sruba_scalenie)
(command "_line" '(0.00000000 13.85000000) '(-12.00000000 6.92500000) "") (ssadd (entlast) azt_sruba_scalenie)
(command "_line" '(-12.00000000 6.92500000) '(-12.00000000 -6.92500000) "") (ssadd (entlast) azt_sruba_scalenie)
(command "_line" '(12.00000000 -6.92500000) '(12.00000000 6.92500000) "") (ssadd (entlast) azt_sruba_scalenie)
(command "_circle" '(0.00000000 0.00000000) "8.00000000") (ssadd (entlast) azt_sruba_scalenie)
(command "_circle" '(0.00000000 0.00000000) "15.00000000") (ssadd (entlast) azt_sruba_scalenie)
(command "_line" '(12.00000000 6.92500000) '(0.00000000 13.85000000) "") (ssadd (entlast) azt_sruba_scalenie)
(command "_circle" '(0.00000000 0.00000000) "11.00000000") (ssadd (entlast) azt_sruba_scalenie)
)

(defun azt_rysuj_osie_gwint_przekr_m16 ()
(command "_line" '(0.00000000 0.00000000) '(16.80000000 0.00000000) "") (ssadd (entlast) azt_sruba_scalenie)
(command "_line" '(-16.80000000 0.00000000) '(0.00000000 0.00000000) "") (ssadd (entlast) azt_sruba_scalenie)
(command "_line" '(0.00000000 0.00000000) '(0.00000000 -19.39000000) "") (ssadd (entlast) azt_sruba_scalenie)
(command "_line" '(0.00000000 19.39000000) '(0.00000000 0.00000000) "") (ssadd (entlast) azt_sruba_scalenie)
)

(defun c:azt_sruba_gwint_m16 ()
(setq azt_sruba_scalenie (ssadd))
(setq azt_aktualna_sruba_gwint_typ "16")
(azt_punkt_wstawienia_sruby_przekr)
(command "_ZOOM" "_SCALE" "10000X")
(azt_ucs_wstawienia_sruby_przekr)
(command "_layer" "_S" "S_VIEW" "")
(azt_rysuj_gwint_przekr_m16)
(command "_layer" "_S" "S_GRIDS" "")
(azt_rysuj_osie_gwint_przekr_m16)
(azt_przywroc_ucs_sruby)
(command "_ZOOM" "_SCALE" "0.0001X")
(command "_layer" "_S" "0" "")
(command "_group" "_C" "*" "" azt_sruba_scalenie "")
(setq azt_sruba_scalenie (ssadd))
)

;#######################   SRUBA M16 - LEB   #######################

(defun azt_rysuj_leb_przekr_m16 ()
(command "_line" '(-12.00000000 -6.92500000) '(0.00000000 -13.85000000) "") (ssadd (entlast) azt_sruba_scalenie)
(command "_line" '(-12.00000000 6.92500000) '(-12.00000000 -6.92500000) "") (ssadd (entlast) azt_sruba_scalenie)
(command "_line" '(0.00000000 13.85000000) '(-12.00000000 6.92500000) "") (ssadd (entlast) azt_sruba_scalenie)
(command "_line" '(0.00000000 -13.85000000) '(12.00000000 -6.92500000) "") (ssadd (entlast) azt_sruba_scalenie)
(command "_circle" '(0.00000000 0.00000000) "11.00000000") (ssadd (entlast) azt_sruba_scalenie)
(command "_line" '(12.00000000 6.92500000) '(0.00000000 13.85000000) "") (ssadd (entlast) azt_sruba_scalenie)
(command "_line" '(12.00000000 -6.92500000) '(12.00000000 6.92500000) "") (ssadd (entlast) azt_sruba_scalenie)
)

(defun azt_rysuj_osie_leb_przekr_m16 ()
(command "_line" '(0.00000000 0.00000000) '(16.80000000 0.00000000) "") (ssadd (entlast) azt_sruba_scalenie)
(command "_line" '(-16.80000000 0.00000000) '(0.00000000 0.00000000) "") (ssadd (entlast) azt_sruba_scalenie)
(command "_line" '(0.00000000 0.00000000) '(0.00000000 -19.39000000) "") (ssadd (entlast) azt_sruba_scalenie)
(command "_line" '(0.00000000 19.39000000) '(0.00000000 0.00000000) "") (ssadd (entlast) azt_sruba_scalenie)
)

(defun c:azt_sruba_leb_m16 ()
(setq azt_sruba_scalenie (ssadd))
(setq azt_aktualna_sruba_leb_typ "16")
(azt_punkt_wstawienia_sruby_przekr)
(command "_ZOOM" "_SCALE" "10000X")
(azt_ucs_wstawienia_sruby_przekr)
(command "_layer" "_S" "S_VIEW" "")
(azt_rysuj_leb_przekr_m16)
(command "_layer" "_S" "S_GRIDS" "")
(azt_rysuj_osie_leb_przekr_m16)
(azt_przywroc_ucs_sruby)
(command "_ZOOM" "_SCALE" "0.0001X")
(command "_layer" "_S" "0" "")
(command "_group" "_C" "*" "" azt_sruba_scalenie "")
(setq azt_sruba_scalenie (ssadd))
)
;#######################   KONIEC SRUBY M16   #######################

;#######################   SRUBA M20  #######################
;#######################   SRUBA M20 - WIDOK   #######################

(defun azt_rysuj_leb_m20 ()
(command "_line" '(-13.00000000 12.97500000) '(-13.00000000 -12.97500000) "") (ssadd (entlast) azt_sruba_scalenie)
(command "_line" '(-13.00000000 0.00000000) '(-13.00000000 12.97500000) "") (ssadd (entlast) azt_sruba_scalenie)
(command "_arc" "_C" '(20.58625000 -0.50000000) "@33.58997155<179" "_A" "15") (ssadd (entlast) azt_sruba_scalenie)
(command "_line" '(-13.00000000 -12.97500000) '(-13.00000000 0.00000000) "") (ssadd (entlast) azt_sruba_scalenie)
(command "_arc" "_C" '(20.58625000 0.50000000) "@33.58997155<166" "_A" "15") (ssadd (entlast) azt_sruba_scalenie)
(command "_line" '(0.00000000 10.00000000) '(0.00000000 17.30000000) "") (ssadd (entlast) azt_sruba_scalenie)
(command "_line" '(0.00000000 0.00000000) '(0.00000000 10.00000000) "") (ssadd (entlast) azt_sruba_scalenie)
(command "_arc" "_C" '(-3.14718750 12.97500000) "@9.85281250<154" "_A" "52") (ssadd (entlast) azt_sruba_scalenie)
(command "_line" '(0.00000000 17.30000000) '(-12.00000000 17.30000000) "") (ssadd (entlast) azt_sruba_scalenie)
(command "_line" '(0.00000000 -8.65000000) '(-12.00000000 -8.65000000) "") (ssadd (entlast) azt_sruba_scalenie)
(command "_line" '(0.00000000 8.65000000) '(0.00000000 -8.65000000) "") (ssadd (entlast) azt_sruba_scalenie)
(command "_line" '(0.00000000 -8.65000000) '(0.00000000 -10.00000000) "") (ssadd (entlast) azt_sruba_scalenie)
(command "_line" '(-12.00000000 -8.65000000) '(0.00000000 -8.65000000) "") (ssadd (entlast) azt_sruba_scalenie)
(command "_line" '(-12.00000000 8.65000000) '(0.00000000 8.65000000) "") (ssadd (entlast) azt_sruba_scalenie)
(command "_line" '(-12.00000000 -17.30000000) '(0.00000000 -17.30000000) "") (ssadd (entlast) azt_sruba_scalenie)
(command "_arc" "_C" '(-3.14718750 -12.97500000) "@9.85281250<154" "_A" "52") (ssadd (entlast) azt_sruba_scalenie)
(command "_line" '(0.00000000 8.65000000) '(-12.00000000 8.65000000) "") (ssadd (entlast) azt_sruba_scalenie)
(command "_line" '(0.00000000 -17.30000000) '(0.00000000 8.65000000) "") (ssadd (entlast) azt_sruba_scalenie)
)

(defun azt_rysuj_trzpien_m20 ()
(command "_pline" '(0.0 10.0) (list azt_aktualne_skleszczenie_sruby 10.0 ) "") (ssadd (entlast) azt_sruba_scalenie)
(command "_pline" '(0.0 -10.0) (list azt_aktualne_skleszczenie_sruby -10.0 ) "") (ssadd (entlast) azt_sruba_scalenie)
)

(defun azt_rysuj_podkladki_m20 ()
(command "_line" '(0.00000000 -18.50000000) '(3.00000000 -18.50000000) "") (ssadd (entlast) azt_sruba_scalenie)
(command "_line" '(0.00000000 -10.00000000) '(0.00000000 -18.50000000) "") (ssadd (entlast) azt_sruba_scalenie)
(command "_line" '(3.00000000 -18.50000000) '(3.00000000 -10.50000000) "") (ssadd (entlast) azt_sruba_scalenie)
(command "_line" '(3.00000000 -18.50000000) '(6.00000000 -18.50000000) "") (ssadd (entlast) azt_sruba_scalenie)
(command "_line" '(3.00000000 -10.50000000) '(3.00000000 -18.50000000) "") (ssadd (entlast) azt_sruba_scalenie)
(command "_line" '(0.00000000 -10.50000000) '(0.00000000 -10.00000000) "") (ssadd (entlast) azt_sruba_scalenie)
(command "_line" '(6.00000000 -10.50000000) '(3.00000000 -10.50000000) "") (ssadd (entlast) azt_sruba_scalenie)
(command "_line" '(6.00000000 -10.00000000) '(6.00000000 -10.50000000) "") (ssadd (entlast) azt_sruba_scalenie)
(command "_line" '(3.00000000 -10.50000000) '(3.00000000 -10.00000000) "") (ssadd (entlast) azt_sruba_scalenie)
(command "_line" '(3.00000000 -10.50000000) '(0.00000000 -10.50000000) "") (ssadd (entlast) azt_sruba_scalenie)
(command "_line" '(3.00000000 -10.00000000) '(3.00000000 -10.50000000) "") (ssadd (entlast) azt_sruba_scalenie)
(command "_line" '(3.00000000 10.00000000) '(3.00000000 18.50000000) "") (ssadd (entlast) azt_sruba_scalenie)
(command "_line" '(3.00000000 10.50000000) '(3.00000000 10.00000000) "") (ssadd (entlast) azt_sruba_scalenie)
(command "_line" '(3.00000000 18.50000000) '(3.00000000 10.50000000) "") (ssadd (entlast) azt_sruba_scalenie)
(command "_line" '(6.00000000 10.50000000) '(6.00000000 10.00000000) "") (ssadd (entlast) azt_sruba_scalenie)
(command "_line" '(3.00000000 10.50000000) '(6.00000000 10.50000000) "") (ssadd (entlast) azt_sruba_scalenie)
(command "_line" '(0.00000000 10.50000000) '(3.00000000 10.50000000) "") (ssadd (entlast) azt_sruba_scalenie)
(command "_line" '(6.00000000 10.50000000) '(6.00000000 18.50000000) "") (ssadd (entlast) azt_sruba_scalenie)
(command "_line" '(6.00000000 -18.50000000) '(6.00000000 -10.50000000) "") (ssadd (entlast) azt_sruba_scalenie)
(command "_line" '(6.00000000 18.50000000) '(0.00000000 18.50000000) "") (ssadd (entlast) azt_sruba_scalenie)
(command "_line" '(0.00000000 10.00000000) '(0.00000000 10.50000000) "") (ssadd (entlast) azt_sruba_scalenie)
(command "_line" '(0.00000000 18.50000000) '(0.00000000 10.00000000) "") (ssadd (entlast) azt_sruba_scalenie)
(command "_line" '(0.00000000 10.00000000) '(6.00000000 10.00000000) "") (ssadd (entlast) azt_sruba_scalenie)
(command "_line" '(0.00000000 -10.00000000) '(6.00000000 -10.00000000) "") (ssadd (entlast) azt_sruba_scalenie)
)

(defun azt_rysuj_nakretke_m20 ()
(command "_arc" "_C" '(15.85281250 12.97500000) "@9.85281250<154" "_A" "52") (ssadd (entlast) azt_sruba_scalenie)
(command "_line" '(21.00000000 8.65000000) '(7.00000000 8.65000000) "") (ssadd (entlast) azt_sruba_scalenie)
(command "_line" '(7.00000000 8.65000000) '(21.00000000 8.65000000) "") (ssadd (entlast) azt_sruba_scalenie)
(command "_arc" "_C" '(-11.58625000 0.50000000) "@33.58997155<359" "_A" "15") (ssadd (entlast) azt_sruba_scalenie)
(command "_arc" "_C" '(12.14718750 12.97500000) "@9.85281250<334" "_A" "52") (ssadd (entlast) azt_sruba_scalenie)
(command "_line" '(7.00000000 17.30000000) '(21.00000000 17.30000000) "") (ssadd (entlast) azt_sruba_scalenie)
(command "_line" '(6.00000000 0.00000000) '(6.00000000 -12.97500000) "") (ssadd (entlast) azt_sruba_scalenie)
(command "_line" '(6.00000000 -10.50000000) '(6.00000000 0.00000000) "") (ssadd (entlast) azt_sruba_scalenie)
(command "_line" '(6.00000000 -10.00000000) '(6.00000000 -10.50000000) "") (ssadd (entlast) azt_sruba_scalenie)
(command "_arc" "_C" '(39.58625000 0.50000000) "@33.58997155<166" "_A" "15") (ssadd (entlast) azt_sruba_scalenie)
(command "_line" '(6.00000000 12.97500000) '(6.00000000 0.00000000) "") (ssadd (entlast) azt_sruba_scalenie)
(command "_line" '(6.00000000 -12.97500000) '(6.00000000 12.97500000) "") (ssadd (entlast) azt_sruba_scalenie)
(command "_line" '(22.00000000 0.00000000) '(22.00000000 12.97500000) "") (ssadd (entlast) azt_sruba_scalenie)
(command "_line" '(21.00000000 -8.65000000) '(7.00000000 -8.65000000) "") (ssadd (entlast) azt_sruba_scalenie)
(command "_line" '(7.00000000 -8.65000000) '(21.00000000 -8.65000000) "") (ssadd (entlast) azt_sruba_scalenie)
(command "_arc" "_C" '(15.85281250 -12.97500000) "@9.85281250<154" "_A" "52") (ssadd (entlast) azt_sruba_scalenie)
(command "_line" '(6.00000000 10.50000000) '(6.00000000 10.00000000) "") (ssadd (entlast) azt_sruba_scalenie)
(command "_line" '(6.00000000 0.00000000) '(6.00000000 10.50000000) "") (ssadd (entlast) azt_sruba_scalenie)
(command "_arc" "_C" '(39.58625000 -0.50000000) "@33.58997155<179" "_A" "15") (ssadd (entlast) azt_sruba_scalenie)
(command "_line" '(22.00000000 -12.97500000) '(22.00000000 0.00000000) "") (ssadd (entlast) azt_sruba_scalenie)
(command "_line" '(22.00000000 -10.00000000) '(22.00000000 -12.97500000) "") (ssadd (entlast) azt_sruba_scalenie)
(command "_line" '(22.00000000 12.97500000) '(22.00000000 10.00000000) "") (ssadd (entlast) azt_sruba_scalenie)
(command "_line" '(21.00000000 -17.30000000) '(7.00000000 -17.30000000) "") (ssadd (entlast) azt_sruba_scalenie)
(command "_arc" "_C" '(12.14718750 -12.97500000) "@9.85281250<334" "_A" "52") (ssadd (entlast) azt_sruba_scalenie)
(command "_arc" "_C" '(-11.58625000 -0.50000000) "@33.58997155<346" "_A" "15") (ssadd (entlast) azt_sruba_scalenie)
)

(defun azt_rysuj_gwint_m20 ()
(command "_line" '(48.00000000 10.00000000) '(50.00000000 8.00000000) "") (ssadd (entlast) azt_sruba_scalenie)
(command "_line" '(22.00000000 10.00000000) '(48.00000000 10.00000000) "") (ssadd (entlast) azt_sruba_scalenie)
(command "_line" '(50.00000000 8.00000000) '(50.00000000 -8.00000000) "") (ssadd (entlast) azt_sruba_scalenie)
(command "_line" '(48.00000000 -10.00000000) '(22.00000000 -10.00000000) "") (ssadd (entlast) azt_sruba_scalenie)
(command "_line" '(50.00000000 -8.00000000) '(48.00000000 -10.00000000) "") (ssadd (entlast) azt_sruba_scalenie)
)

(defun azt_rysuj_niewidoczna_czesc_sruby_m20 ()
(command "_line" '(4.00000000 -8.00000000) '(2.00000000 -10.00000000) "") (ssadd (entlast) azt_sruba_scalenie)
(command "_line" '(2.00000000 -10.00000000) '(4.00000000 -8.00000000) "") (ssadd (entlast) azt_sruba_scalenie)
(command "_line" '(4.00000000 -8.00000000) '(4.00000000 -10.00000000) "") (ssadd (entlast) azt_sruba_scalenie)
(command "_line" '(4.00000000 8.00000000) '(4.00000000 -8.00000000) "") (ssadd (entlast) azt_sruba_scalenie)
(command "_line" '(2.00000000 10.00000000) '(4.00000000 8.00000000) "") (ssadd (entlast) azt_sruba_scalenie)
(command "_line" '(4.00000000 8.00000000) '(4.00000000 10.00000000) "") (ssadd (entlast) azt_sruba_scalenie)
(command "_line" '(4.00000000 10.00000000) '(4.00000000 8.00000000) "") (ssadd (entlast) azt_sruba_scalenie)
(command "_line" '(4.00000000 -10.00000000) '(4.00000000 -8.00000000) "") (ssadd (entlast) azt_sruba_scalenie)
(command "_line" '(48.00000000 10.00000000) '(48.00000000 8.00000000) "") (ssadd (entlast) azt_sruba_scalenie)
(command "_line" '(48.00000000 8.00000000) '(50.00000000 8.00000000) "") (ssadd (entlast) azt_sruba_scalenie)
(command "_line" '(50.00000000 8.00000000) '(4.00000000 8.00000000) "") (ssadd (entlast) azt_sruba_scalenie)
(command "_line" '(48.00000000 -10.00000000) '(48.00000000 10.00000000) "") (ssadd (entlast) azt_sruba_scalenie)
(command "_line" '(4.00000000 -8.00000000) '(50.00000000 -8.00000000) "") (ssadd (entlast) azt_sruba_scalenie)
(command "_line" '(50.00000000 -8.00000000) '(48.00000000 -8.00000000) "") (ssadd (entlast) azt_sruba_scalenie)
(command "_line" '(48.00000000 -8.00000000) '(48.00000000 -10.00000000) "") (ssadd (entlast) azt_sruba_scalenie)
)

(defun c:azt_sruba_widok_m20 ()
  (setq azt_sruba_scalenie (ssadd))
  (setq azt_aktualna_sruba_widok_typ "20")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m20)
  (setvar "CECOLOR" "126")
  (azt_rysuj_trzpien_m20)
  (setvar "CECOLOR" "127")
  (azt_rysuj_niewidoczna_czesc_sruby_m20)
  (setvar "CECOLOR" "128")
  (azt_rysuj_podkladki_m20)
  (azt_rysuj_nakretke_m20)
  (azt_rysuj_gwint_m20)
  (azt_wprowadz_skleszczenie_sruby)
  (azt_przywroc_ucs_sruby)
  (command "_ZOOM" "_SCALE" "0.0001X")
  (command "_layer" "_S" "0" "")
  (setvar "CECOLOR" "BYLAYER")
  (command "_group" "_C" "*" "" azt_sruba_scalenie "")
  (setq azt_sruba_scalenie (ssadd))
)

;#######################   SRUBA M20 - GWINT   #######################

(defun azt_rysuj_gwint_przekr_m20 ()
(command "_line" '(-15.00000000 -8.65000000) '(0.00000000 -17.30000000) "") (ssadd (entlast) azt_sruba_scalenie)
(command "_line" '(0.00000000 -17.30000000) '(15.00000000 -8.65000000) "") (ssadd (entlast) azt_sruba_scalenie)
(command "_line" '(0.00000000 17.30000000) '(-15.00000000 8.65000000) "") (ssadd (entlast) azt_sruba_scalenie)
(command "_line" '(-15.00000000 8.65000000) '(-15.00000000 -8.65000000) "") (ssadd (entlast) azt_sruba_scalenie)
(command "_line" '(15.00000000 -8.65000000) '(15.00000000 8.65000000) "") (ssadd (entlast) azt_sruba_scalenie)
(command "_circle" '(0.00000000 0.00000000) "10.00000000") (ssadd (entlast) azt_sruba_scalenie)
(command "_circle" '(0.00000000 0.00000000) "18.50000000") (ssadd (entlast) azt_sruba_scalenie)
(command "_line" '(15.00000000 8.65000000) '(0.00000000 17.30000000) "") (ssadd (entlast) azt_sruba_scalenie)
(command "_circle" '(0.00000000 0.00000000) "14.00000000") (ssadd (entlast) azt_sruba_scalenie)
)

(defun azt_rysuj_osie_gwint_przekr_m20 ()
(command "_line" '(0.00000000 0.00000000) '(21.00000000 0.00000000) "") (ssadd (entlast) azt_sruba_scalenie)
(command "_line" '(-21.00000000 0.00000000) '(0.00000000 0.00000000) "") (ssadd (entlast) azt_sruba_scalenie)
(command "_line" '(0.00000000 0.00000000) '(0.00000000 -24.22000000) "") (ssadd (entlast) azt_sruba_scalenie)
(command "_line" '(0.00000000 24.22000000) '(0.00000000 0.00000000) "") (ssadd (entlast) azt_sruba_scalenie)
)

(defun c:azt_sruba_gwint_m20 ()
(setq azt_sruba_scalenie (ssadd))
(setq azt_aktualna_sruba_gwint_typ "20")
(azt_punkt_wstawienia_sruby_przekr)
(command "_ZOOM" "_SCALE" "10000X")
(azt_ucs_wstawienia_sruby_przekr)
(command "_layer" "_S" "S_VIEW" "")
(azt_rysuj_gwint_przekr_m20)
(command "_layer" "_S" "S_GRIDS" "")
(azt_rysuj_osie_gwint_przekr_m20)
(azt_przywroc_ucs_sruby)
(command "_ZOOM" "_SCALE" "0.0001X")
(command "_layer" "_S" "0" "")
(command "_group" "_C" "*" "" azt_sruba_scalenie "")
(setq azt_sruba_scalenie (ssadd))
)


;#######################   SRUBA M20 - LEB   #######################

(defun azt_rysuj_leb_przekr_m20 ()
(command "_line" '(-15.00000000 -8.65000000) '(0.00000000 -17.30000000) "") (ssadd (entlast) azt_sruba_scalenie)
(command "_line" '(-15.00000000 8.65000000) '(-15.00000000 -8.65000000) "") (ssadd (entlast) azt_sruba_scalenie)
(command "_line" '(0.00000000 17.30000000) '(-15.00000000 8.65000000) "") (ssadd (entlast) azt_sruba_scalenie)
(command "_line" '(0.00000000 -17.30000000) '(15.00000000 -8.65000000) "") (ssadd (entlast) azt_sruba_scalenie)
(command "_circle" '(0.00000000 0.00000000) "14.00000000") (ssadd (entlast) azt_sruba_scalenie)
(command "_line" '(15.00000000 8.65000000) '(0.00000000 17.30000000) "") (ssadd (entlast) azt_sruba_scalenie)
(command "_line" '(15.00000000 -8.65000000) '(15.00000000 8.65000000) "") (ssadd (entlast) azt_sruba_scalenie)
)

(defun azt_rysuj_osie_leb_przekr_m20 ()
(command "_line" '(0.00000000 0.00000000) '(21.00000000 0.00000000) "") (ssadd (entlast) azt_sruba_scalenie)
(command "_line" '(-21.00000000 0.00000000) '(0.00000000 0.00000000) "") (ssadd (entlast) azt_sruba_scalenie)
(command "_line" '(0.00000000 0.00000000) '(0.00000000 -24.22000000) "") (ssadd (entlast) azt_sruba_scalenie)
(command "_line" '(0.00000000 24.22000000) '(0.00000000 0.00000000) "") (ssadd (entlast) azt_sruba_scalenie)
)

(defun c:azt_sruba_leb_m20 ()
(setq azt_sruba_scalenie (ssadd))
(setq azt_aktualna_sruba_leb_typ "20")
(azt_punkt_wstawienia_sruby_przekr)
(command "_ZOOM" "_SCALE" "10000X")
(azt_ucs_wstawienia_sruby_przekr)
(command "_layer" "_S" "S_VIEW" "")
(azt_rysuj_leb_przekr_m20)
(command "_layer" "_S" "S_GRIDS" "")
(azt_rysuj_osie_leb_przekr_m20)
(azt_przywroc_ucs_sruby)
(command "_ZOOM" "_SCALE" "0.0001X")
(command "_layer" "_S" "0" "")
(command "_group" "_C" "*" "" azt_sruba_scalenie "")
(setq azt_sruba_scalenie (ssadd))
)

;#######################   KONIEC SRUBY M20   #######################

;#######################   SRUBA M24   #######################
;#######################   SRUBA M24 - WIDOK   #######################

(defun azt_rysuj_leb_m24 ()
(command "_line" '(-15.00000000 15.60000000) '(-15.00000000 -15.60000000) "") (ssadd (entlast) azt_sruba_scalenie)
(command "_line" '(-15.00000000 0.00000000) '(-15.00000000 15.60000000) "") (ssadd (entlast) azt_sruba_scalenie)
(command "_arc" "_C" '(34.38000000 -0.50000000) "@49.38253132<179" "_A" "12") (ssadd (entlast) azt_sruba_scalenie)
(command "_line" '(-15.00000000 -15.60000000) '(-15.00000000 0.00000000) "") (ssadd (entlast) azt_sruba_scalenie)
(command "_arc" "_C" '(34.38000000 0.50000000) "@49.38253132<168" "_A" "12") (ssadd (entlast) azt_sruba_scalenie)
(command "_line" '(0.00000000 12.00000000) '(0.00000000 20.80000000) "") (ssadd (entlast) azt_sruba_scalenie)
(command "_line" '(0.00000000 0.00000000) '(0.00000000 12.00000000) "") (ssadd (entlast) azt_sruba_scalenie)
(command "_arc" "_C" '(-0.98000000 15.60000000) "@14.02000000<158" "_A" "44") (ssadd (entlast) azt_sruba_scalenie)
(command "_line" '(0.00000000 20.80000000) '(-14.00000000 20.80000000) "") (ssadd (entlast) azt_sruba_scalenie)
(command "_line" '(0.00000000 -10.40000000) '(-14.00000000 -10.40000000) "") (ssadd (entlast) azt_sruba_scalenie)
(command "_line" '(0.00000000 10.40000000) '(0.00000000 -10.40000000) "") (ssadd (entlast) azt_sruba_scalenie)
(command "_line" '(0.00000000 -10.40000000) '(0.00000000 -12.00000000) "") (ssadd (entlast) azt_sruba_scalenie)
(command "_line" '(-14.00000000 -10.40000000) '(0.00000000 -10.40000000) "") (ssadd (entlast) azt_sruba_scalenie)
(command "_line" '(-14.00000000 10.40000000) '(0.00000000 10.40000000) "") (ssadd (entlast) azt_sruba_scalenie)
(command "_line" '(-14.00000000 -20.80000000) '(0.00000000 -20.80000000) "") (ssadd (entlast) azt_sruba_scalenie)
(command "_arc" "_C" '(-0.98000000 -15.60000000) "@14.02000000<158" "_A" "44") (ssadd (entlast) azt_sruba_scalenie)
(command "_line" '(0.00000000 10.40000000) '(-14.00000000 10.40000000) "") (ssadd (entlast) azt_sruba_scalenie)
(command "_line" '(0.00000000 -20.80000000) '(0.00000000 10.40000000) "") (ssadd (entlast) azt_sruba_scalenie)
)

(defun azt_rysuj_trzpien_m24 ()
(command "_pline" '(0.0 12.0) (list azt_aktualne_skleszczenie_sruby 12.0 ) "") (ssadd (entlast) azt_sruba_scalenie)
(command "_pline" '(0.0 -12.0) (list azt_aktualne_skleszczenie_sruby -12.0 ) "") (ssadd (entlast) azt_sruba_scalenie)
)

(defun azt_rysuj_podkladki_m24 ()
(command "_line" '(4.00000000 -22.00000000) '(4.00000000 -12.50000000) "") (ssadd (entlast) azt_sruba_scalenie)
(command "_line" '(0.00000000 -22.00000000) '(4.00000000 -22.00000000) "") (ssadd (entlast) azt_sruba_scalenie)
(command "_line" '(0.00000000 -12.00000000) '(0.00000000 -22.00000000) "") (ssadd (entlast) azt_sruba_scalenie)
(command "_line" '(8.00000000 -22.00000000) '(8.00000000 -12.50000000) "") (ssadd (entlast) azt_sruba_scalenie)
(command "_line" '(4.00000000 -22.00000000) '(8.00000000 -22.00000000) "") (ssadd (entlast) azt_sruba_scalenie)
(command "_line" '(4.00000000 -12.50000000) '(4.00000000 -22.00000000) "") (ssadd (entlast) azt_sruba_scalenie)
(command "_line" '(4.00000000 -12.50000000) '(4.00000000 -12.00000000) "") (ssadd (entlast) azt_sruba_scalenie)
(command "_line" '(8.00000000 -12.50000000) '(4.00000000 -12.50000000) "") (ssadd (entlast) azt_sruba_scalenie)
(command "_line" '(8.00000000 -12.00000000) '(8.00000000 -12.50000000) "") (ssadd (entlast) azt_sruba_scalenie)
(command "_line" '(0.00000000 -12.50000000) '(0.00000000 -12.00000000) "") (ssadd (entlast) azt_sruba_scalenie)
(command "_line" '(4.00000000 -12.50000000) '(0.00000000 -12.50000000) "") (ssadd (entlast) azt_sruba_scalenie)
(command "_line" '(4.00000000 -12.00000000) '(4.00000000 -12.50000000) "") (ssadd (entlast) azt_sruba_scalenie)
(command "_line" '(4.00000000 12.50000000) '(8.00000000 12.50000000) "") (ssadd (entlast) azt_sruba_scalenie)
(command "_line" '(4.00000000 22.00000000) '(4.00000000 12.50000000) "") (ssadd (entlast) azt_sruba_scalenie)
(command "_line" '(4.00000000 12.00000000) '(4.00000000 22.00000000) "") (ssadd (entlast) azt_sruba_scalenie)
(command "_line" '(0.00000000 -12.00000000) '(8.00000000 -12.00000000) "") (ssadd (entlast) azt_sruba_scalenie)
(command "_line" '(0.00000000 12.00000000) '(8.00000000 12.00000000) "") (ssadd (entlast) azt_sruba_scalenie)
(command "_line" '(8.00000000 12.50000000) '(8.00000000 12.00000000) "") (ssadd (entlast) azt_sruba_scalenie)
(command "_line" '(0.00000000 22.00000000) '(0.00000000 12.00000000) "") (ssadd (entlast) azt_sruba_scalenie)
(command "_line" '(8.00000000 22.00000000) '(0.00000000 22.00000000) "") (ssadd (entlast) azt_sruba_scalenie)
(command "_line" '(8.00000000 12.50000000) '(8.00000000 22.00000000) "") (ssadd (entlast) azt_sruba_scalenie)
(command "_line" '(4.00000000 12.50000000) '(4.00000000 12.00000000) "") (ssadd (entlast) azt_sruba_scalenie)
(command "_line" '(0.00000000 12.50000000) '(4.00000000 12.50000000) "") (ssadd (entlast) azt_sruba_scalenie)
(command "_line" '(0.00000000 12.00000000) '(0.00000000 12.50000000) "") (ssadd (entlast) azt_sruba_scalenie)
)

(defun azt_rysuj_nakretke_m24 ()
(command "_arc" "_C" '(22.02000000 15.60000000) "@14.02000000<158" "_A" "44") (ssadd (entlast) azt_sruba_scalenie)
(command "_line" '(26.00000000 10.40000000) '(9.00000000 10.40000000) "") (ssadd (entlast) azt_sruba_scalenie)
(command "_line" '(9.00000000 10.40000000) '(26.00000000 10.40000000) "") (ssadd (entlast) azt_sruba_scalenie)
(command "_arc" "_C" '(-22.38000000 0.50000000) "@49.38253132<359" "_A" "12") (ssadd (entlast) azt_sruba_scalenie)
(command "_arc" "_C" '(12.98000000 15.60000000) "@14.02000000<338" "_A" "44") (ssadd (entlast) azt_sruba_scalenie)
(command "_line" '(9.00000000 20.80000000) '(26.00000000 20.80000000) "") (ssadd (entlast) azt_sruba_scalenie)
(command "_line" '(8.00000000 0.00000000) '(8.00000000 -15.60000000) "") (ssadd (entlast) azt_sruba_scalenie)
(command "_line" '(8.00000000 -12.50000000) '(8.00000000 0.00000000) "") (ssadd (entlast) azt_sruba_scalenie)
(command "_line" '(8.00000000 -12.00000000) '(8.00000000 -12.50000000) "") (ssadd (entlast) azt_sruba_scalenie)
(command "_arc" "_C" '(57.38000000 0.50000000) "@49.38253132<168" "_A" "12") (ssadd (entlast) azt_sruba_scalenie)
(command "_line" '(8.00000000 15.60000000) '(8.00000000 0.00000000) "") (ssadd (entlast) azt_sruba_scalenie)
(command "_line" '(8.00000000 -15.60000000) '(8.00000000 15.60000000) "") (ssadd (entlast) azt_sruba_scalenie)
(command "_line" '(27.00000000 0.00000000) '(27.00000000 15.60000000) "") (ssadd (entlast) azt_sruba_scalenie)
(command "_line" '(26.00000000 -10.40000000) '(9.00000000 -10.40000000) "") (ssadd (entlast) azt_sruba_scalenie)
(command "_line" '(9.00000000 -10.40000000) '(26.00000000 -10.40000000) "") (ssadd (entlast) azt_sruba_scalenie)
(command "_arc" "_C" '(22.02000000 -15.60000000) "@14.02000000<158" "_A" "44") (ssadd (entlast) azt_sruba_scalenie)
(command "_line" '(8.00000000 12.50000000) '(8.00000000 12.00000000) "") (ssadd (entlast) azt_sruba_scalenie)
(command "_line" '(8.00000000 0.00000000) '(8.00000000 12.50000000) "") (ssadd (entlast) azt_sruba_scalenie)
(command "_arc" "_C" '(57.38000000 -0.50000000) "@49.38253132<179" "_A" "12") (ssadd (entlast) azt_sruba_scalenie)
(command "_line" '(27.00000000 -15.60000000) '(27.00000000 0.00000000) "") (ssadd (entlast) azt_sruba_scalenie)
(command "_line" '(27.00000000 -12.00000000) '(27.00000000 -15.60000000) "") (ssadd (entlast) azt_sruba_scalenie)
(command "_line" '(27.00000000 15.60000000) '(27.00000000 12.00000000) "") (ssadd (entlast) azt_sruba_scalenie)
(command "_line" '(26.00000000 -20.80000000) '(9.00000000 -20.80000000) "") (ssadd (entlast) azt_sruba_scalenie)
(command "_arc" "_C" '(12.98000000 -15.60000000) "@14.02000000<338" "_A" "44") (ssadd (entlast) azt_sruba_scalenie)
(command "_arc" "_C" '(-22.38000000 -0.50000000) "@49.38253132<348" "_A" "12") (ssadd (entlast) azt_sruba_scalenie)
)

(defun azt_rysuj_gwint_m24 ()
(command "_line" '(58.00000000 12.00000000) '(60.00000000 10.00000000) "") (ssadd (entlast) azt_sruba_scalenie)
(command "_line" '(27.00000000 12.00000000) '(58.00000000 12.00000000) "") (ssadd (entlast) azt_sruba_scalenie)
(command "_line" '(60.00000000 10.00000000) '(60.00000000 -10.00000000) "") (ssadd (entlast) azt_sruba_scalenie)
(command "_line" '(58.00000000 -12.00000000) '(27.00000000 -12.00000000) "") (ssadd (entlast) azt_sruba_scalenie)
(command "_line" '(60.00000000 -10.00000000) '(58.00000000 -12.00000000) "") (ssadd (entlast) azt_sruba_scalenie)
)

(defun azt_rysuj_niewidoczna_czesc_sruby_m24 ()
(command "_line" '(6.00000000 -10.00000000) '(4.00000000 -12.00000000) "") (ssadd (entlast) azt_sruba_scalenie)
(command "_line" '(4.00000000 -12.00000000) '(6.00000000 -10.00000000) "") (ssadd (entlast) azt_sruba_scalenie)
(command "_line" '(6.00000000 -10.00000000) '(6.00000000 -12.00000000) "") (ssadd (entlast) azt_sruba_scalenie)
(command "_line" '(6.00000000 10.00000000) '(6.00000000 -10.00000000) "") (ssadd (entlast) azt_sruba_scalenie)
(command "_line" '(4.00000000 12.00000000) '(6.00000000 10.00000000) "") (ssadd (entlast) azt_sruba_scalenie)
(command "_line" '(6.00000000 10.00000000) '(6.00000000 12.00000000) "") (ssadd (entlast) azt_sruba_scalenie)
(command "_line" '(6.00000000 12.00000000) '(6.00000000 10.00000000) "") (ssadd (entlast) azt_sruba_scalenie)
(command "_line" '(6.00000000 -12.00000000) '(6.00000000 -10.00000000) "") (ssadd (entlast) azt_sruba_scalenie)
(command "_line" '(58.00000000 12.00000000) '(58.00000000 10.00000000) "") (ssadd (entlast) azt_sruba_scalenie)
(command "_line" '(58.00000000 10.00000000) '(60.00000000 10.00000000) "") (ssadd (entlast) azt_sruba_scalenie)
(command "_line" '(60.00000000 10.00000000) '(6.00000000 10.00000000) "") (ssadd (entlast) azt_sruba_scalenie)
(command "_line" '(58.00000000 -12.00000000) '(58.00000000 12.00000000) "") (ssadd (entlast) azt_sruba_scalenie)
(command "_line" '(6.00000000 -10.00000000) '(60.00000000 -10.00000000) "") (ssadd (entlast) azt_sruba_scalenie)
(command "_line" '(60.00000000 -10.00000000) '(58.00000000 -10.00000000) "") (ssadd (entlast) azt_sruba_scalenie)
(command "_line" '(58.00000000 -10.00000000) '(58.00000000 -12.00000000) "") (ssadd (entlast) azt_sruba_scalenie)
)

(defun c:azt_sruba_widok_m24 ()
  (setq azt_sruba_scalenie (ssadd))
  (setq azt_aktualna_sruba_widok_typ "24")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m24)
  (setvar "CECOLOR" "126")
  (azt_rysuj_trzpien_m24)
  (setvar "CECOLOR" "127")
  (azt_rysuj_niewidoczna_czesc_sruby_m24)
  (setvar "CECOLOR" "128")
  (azt_rysuj_podkladki_m24)
  (azt_rysuj_nakretke_m24)
  (azt_rysuj_gwint_m24)
  (azt_wprowadz_skleszczenie_sruby)
  (azt_przywroc_ucs_sruby)
  (command "_ZOOM" "_SCALE" "0.0001X")
  (command "_layer" "_S" "0" "")
  (setvar "CECOLOR" "BYLAYER")
  (command "_group" "_C" "*" "" azt_sruba_scalenie "")
  (setq azt_sruba_scalenie (ssadd))
)

;#######################   SRUBA M24 - GWINT   #######################

(defun azt_rysuj_gwint_przekr_m24 ()
(command "_line" '(-18.00000000 -10.40000000) '(0.00000000 -20.80000000) "") (ssadd (entlast) azt_sruba_scalenie)
(command "_line" '(0.00000000 -20.80000000) '(18.00000000 -10.40000000) "") (ssadd (entlast) azt_sruba_scalenie)
(command "_line" '(0.00000000 20.80000000) '(-18.00000000 10.40000000) "") (ssadd (entlast) azt_sruba_scalenie)
(command "_line" '(-18.00000000 10.40000000) '(-18.00000000 -10.40000000) "") (ssadd (entlast) azt_sruba_scalenie)
(command "_line" '(18.00000000 -10.40000000) '(18.00000000 10.40000000) "") (ssadd (entlast) azt_sruba_scalenie)
(command "_circle" '(0.00000000 0.00000000) "12.00000000") (ssadd (entlast) azt_sruba_scalenie)
(command "_circle" '(0.00000000 0.00000000) "22.00000000") (ssadd (entlast) azt_sruba_scalenie)
(command "_line" '(18.00000000 10.40000000) '(0.00000000 20.80000000) "") (ssadd (entlast) azt_sruba_scalenie)
(command "_circle" '(0.00000000 0.00000000) "17.00000000") (ssadd (entlast) azt_sruba_scalenie)
)

(defun azt_rysuj_osie_gwint_przekr_m24 ()
(command "_line" '(0.00000000 0.00000000) '(25.20000000 0.00000000) "") (ssadd (entlast) azt_sruba_scalenie)
(command "_line" '(-25.20000000 0.00000000) '(0.00000000 0.00000000) "") (ssadd (entlast) azt_sruba_scalenie)
(command "_line" '(0.00000000 0.00000000) '(0.00000000 -29.12000000) "") (ssadd (entlast) azt_sruba_scalenie)
(command "_line" '(0.00000000 29.12000000) '(0.00000000 0.00000000) "") (ssadd (entlast) azt_sruba_scalenie)
)

(defun c:azt_sruba_gwint_m24 ()
(setq azt_sruba_scalenie (ssadd))
(setq azt_aktualna_sruba_gwint_typ "24")
(azt_punkt_wstawienia_sruby_przekr)
(command "_ZOOM" "_SCALE" "10000X")
(azt_ucs_wstawienia_sruby_przekr)
(command "_layer" "_S" "S_VIEW" "")
(azt_rysuj_gwint_przekr_m24)
(command "_layer" "_S" "S_GRIDS" "")
(azt_rysuj_osie_gwint_przekr_m24)
(azt_przywroc_ucs_sruby)
(command "_ZOOM" "_SCALE" "0.0001X")
(command "_layer" "_S" "0" "")
(command "_group" "_C" "*" "" azt_sruba_scalenie "")
(setq azt_sruba_scalenie (ssadd))
)

;#######################   SRUBA M24 - LEB   #######################

(defun azt_rysuj_leb_przekr_m24 ()
(command "_line" '(-18.00000000 -10.40000000) '(0.00000000 -20.80000000) "") (ssadd (entlast) azt_sruba_scalenie)
(command "_line" '(-18.00000000 10.40000000) '(-18.00000000 -10.40000000) "") (ssadd (entlast) azt_sruba_scalenie)
(command "_line" '(0.00000000 20.80000000) '(-18.00000000 10.40000000) "") (ssadd (entlast) azt_sruba_scalenie)
(command "_line" '(0.00000000 -20.80000000) '(18.00000000 -10.40000000) "") (ssadd (entlast) azt_sruba_scalenie)
(command "_circle" '(0.00000000 0.00000000) "17.00000000") (ssadd (entlast) azt_sruba_scalenie)
(command "_line" '(18.00000000 10.40000000) '(0.00000000 20.80000000) "") (ssadd (entlast) azt_sruba_scalenie)
(command "_line" '(18.00000000 -10.40000000) '(18.00000000 10.40000000) "") (ssadd (entlast) azt_sruba_scalenie)
)

(defun azt_rysuj_osie_leb_przekr_m24 ()
(command "_line" '(0.00000000 0.00000000) '(25.20000000 0.00000000) "") (ssadd (entlast) azt_sruba_scalenie)
(command "_line" '(-25.20000000 0.00000000) '(0.00000000 0.00000000) "") (ssadd (entlast) azt_sruba_scalenie)
(command "_line" '(0.00000000 0.00000000) '(0.00000000 -29.12000000) "") (ssadd (entlast) azt_sruba_scalenie)
(command "_line" '(0.00000000 29.12000000) '(0.00000000 0.00000000) "") (ssadd (entlast) azt_sruba_scalenie)
)

(defun c:azt_sruba_leb_m24 ()
(setq azt_sruba_scalenie (ssadd))
(setq azt_aktualna_sruba_leb_typ "24")
(azt_punkt_wstawienia_sruby_przekr)
(command "_ZOOM" "_SCALE" "10000X")
(azt_ucs_wstawienia_sruby_przekr)
(command "_layer" "_S" "S_VIEW" "")
(azt_rysuj_leb_przekr_m24)
(command "_layer" "_S" "S_GRIDS" "")
(azt_rysuj_osie_leb_przekr_m24)
(azt_przywroc_ucs_sruby)
(command "_ZOOM" "_SCALE" "0.0001X")
(command "_layer" "_S" "0" "")
(command "_group" "_C" "*" "" azt_sruba_scalenie "")
(setq azt_sruba_scalenie (ssadd))
)

;#######################   KONIEC SRUBY M24   #######################

;#######################   SRUBA M30   #######################
;#######################   SRUBA M30 - WIDOK   #######################

(defun azt_rysuj_leb_m30 ()
(command "_line" '(-19.00000000 19.91250000) '(-19.00000000 -19.91250000) "") (ssadd (entlast) azt_sruba_scalenie)
(command "_line" '(-19.00000000 0.00000000) '(-19.00000000 19.91250000) "") (ssadd (entlast) azt_sruba_scalenie)
(command "_arc" "_C" '(62.97531250 -0.50000000) "@81.97683734<180" "_A" "9") (ssadd (entlast) azt_sruba_scalenie)
(command "_line" '(-19.00000000 -19.91250000) '(-19.00000000 0.00000000) "") (ssadd (entlast) azt_sruba_scalenie)
(command "_arc" "_C" '(62.97531250 0.50000000) "@81.97683734<171" "_A" "9") (ssadd (entlast) azt_sruba_scalenie)
(command "_line" '(0.00000000 15.00000000) '(0.00000000 26.55000000) "") (ssadd (entlast) azt_sruba_scalenie)
(command "_line" '(0.00000000 0.00000000) '(0.00000000 15.00000000) "") (ssadd (entlast) azt_sruba_scalenie)
(command "_arc" "_C" '(3.52820312 19.91250000) "@22.52820312<163" "_A" "34") (ssadd (entlast) azt_sruba_scalenie)
(command "_line" '(0.00000000 26.55000000) '(-18.00000000 26.55000000) "") (ssadd (entlast) azt_sruba_scalenie)
(command "_line" '(0.00000000 -13.27500000) '(-18.00000000 -13.27500000) "") (ssadd (entlast) azt_sruba_scalenie)
(command "_line" '(0.00000000 13.27500000) '(0.00000000 -13.27500000) "") (ssadd (entlast) azt_sruba_scalenie)
(command "_line" '(0.00000000 -13.27500000) '(0.00000000 -15.00000000) "") (ssadd (entlast) azt_sruba_scalenie)
(command "_line" '(-18.00000000 -13.27500000) '(0.00000000 -13.27500000) "") (ssadd (entlast) azt_sruba_scalenie)
(command "_line" '(-18.00000000 13.27500000) '(0.00000000 13.27500000) "") (ssadd (entlast) azt_sruba_scalenie)
(command "_line" '(-18.00000000 -26.55000000) '(0.00000000 -26.55000000) "") (ssadd (entlast) azt_sruba_scalenie)
(command "_arc" "_C" '(3.52820313 -19.91250000) "@22.52820313<163" "_A" "34") (ssadd (entlast) azt_sruba_scalenie)
(command "_line" '(0.00000000 13.27500000) '(-18.00000000 13.27500000) "") (ssadd (entlast) azt_sruba_scalenie)
(command "_line" '(0.00000000 -26.55000000) '(0.00000000 13.27500000) "") (ssadd (entlast) azt_sruba_scalenie)
)

(defun azt_rysuj_trzpien_m30 ()
(command "_pline" '(0.0 15.0) (list azt_aktualne_skleszczenie_sruby 15.0 ) "") (ssadd (entlast) azt_sruba_scalenie)
(command "_pline" '(0.0 -15.0) (list azt_aktualne_skleszczenie_sruby -15.0 ) "") (ssadd (entlast) azt_sruba_scalenie)
)

(defun azt_rysuj_podkladki_m30 ()
(command "_line" '(5.00000000 -28.00000000) '(5.00000000 -15.50000000) "") (ssadd (entlast) azt_sruba_scalenie)
(command "_line" '(0.00000000 -28.00000000) '(5.00000000 -28.00000000) "") (ssadd (entlast) azt_sruba_scalenie)
(command "_line" '(0.00000000 -15.00000000) '(0.00000000 -28.00000000) "") (ssadd (entlast) azt_sruba_scalenie)
(command "_line" '(10.00000000 -28.00000000) '(10.00000000 -15.50000000) "") (ssadd (entlast) azt_sruba_scalenie)
(command "_line" '(5.00000000 -28.00000000) '(10.00000000 -28.00000000) "") (ssadd (entlast) azt_sruba_scalenie)
(command "_line" '(5.00000000 -15.50000000) '(5.00000000 -28.00000000) "") (ssadd (entlast) azt_sruba_scalenie)
(command "_line" '(5.00000000 -15.50000000) '(5.00000000 -15.00000000) "") (ssadd (entlast) azt_sruba_scalenie)
(command "_line" '(10.00000000 -15.50000000) '(5.00000000 -15.50000000) "") (ssadd (entlast) azt_sruba_scalenie)
(command "_line" '(10.00000000 -15.00000000) '(10.00000000 -15.50000000) "") (ssadd (entlast) azt_sruba_scalenie)
(command "_line" '(0.00000000 -15.50000000) '(0.00000000 -15.00000000) "") (ssadd (entlast) azt_sruba_scalenie)
(command "_line" '(5.00000000 -15.50000000) '(0.00000000 -15.50000000) "") (ssadd (entlast) azt_sruba_scalenie)
(command "_line" '(5.00000000 -15.00000000) '(5.00000000 -15.50000000) "") (ssadd (entlast) azt_sruba_scalenie)
(command "_line" '(5.00000000 15.50000000) '(10.00000000 15.50000000) "") (ssadd (entlast) azt_sruba_scalenie)
(command "_line" '(5.00000000 28.00000000) '(5.00000000 15.50000000) "") (ssadd (entlast) azt_sruba_scalenie)
(command "_line" '(5.00000000 15.00000000) '(5.00000000 28.00000000) "") (ssadd (entlast) azt_sruba_scalenie)
(command "_line" '(0.00000000 -15.00000000) '(10.00000000 -15.00000000) "") (ssadd (entlast) azt_sruba_scalenie)
(command "_line" '(0.00000000 15.00000000) '(10.00000000 15.00000000) "") (ssadd (entlast) azt_sruba_scalenie)
(command "_line" '(10.00000000 15.50000000) '(10.00000000 15.00000000) "") (ssadd (entlast) azt_sruba_scalenie)
(command "_line" '(0.00000000 28.00000000) '(0.00000000 15.00000000) "") (ssadd (entlast) azt_sruba_scalenie)
(command "_line" '(10.00000000 28.00000000) '(0.00000000 28.00000000) "") (ssadd (entlast) azt_sruba_scalenie)
(command "_line" '(10.00000000 15.50000000) '(10.00000000 28.00000000) "") (ssadd (entlast) azt_sruba_scalenie)
(command "_line" '(5.00000000 15.50000000) '(5.00000000 15.00000000) "") (ssadd (entlast) azt_sruba_scalenie)
(command "_line" '(0.00000000 15.50000000) '(5.00000000 15.50000000) "") (ssadd (entlast) azt_sruba_scalenie)
(command "_line" '(0.00000000 15.00000000) '(0.00000000 15.50000000) "") (ssadd (entlast) azt_sruba_scalenie)
)

(defun azt_rysuj_nakretke_m30 ()
(command "_arc" "_C" '(32.52820312 19.91250000) "@22.52820312<163" "_A" "34") (ssadd (entlast) azt_sruba_scalenie)
(command "_line" '(33.00000000 13.27500000) '(11.00000000 13.27500000) "") (ssadd (entlast) azt_sruba_scalenie)
(command "_line" '(11.00000000 13.27500000) '(33.00000000 13.27500000) "") (ssadd (entlast) azt_sruba_scalenie)
(command "_arc" "_C" '(-47.97531250 0.50000000) "@81.97683734<0" "_A" "9") (ssadd (entlast) azt_sruba_scalenie)
(command "_arc" "_C" '(11.47179687 19.91250000) "@22.52820313<343" "_A" "34") (ssadd (entlast) azt_sruba_scalenie)
(command "_line" '(11.00000000 26.55000000) '(33.00000000 26.55000000) "") (ssadd (entlast) azt_sruba_scalenie)
(command "_line" '(10.00000000 0.00000000) '(10.00000000 -19.91250000) "") (ssadd (entlast) azt_sruba_scalenie)
(command "_line" '(10.00000000 -15.50000000) '(10.00000000 0.00000000) "") (ssadd (entlast) azt_sruba_scalenie)
(command "_line" '(10.00000000 -15.00000000) '(10.00000000 -15.50000000) "") (ssadd (entlast) azt_sruba_scalenie)
(command "_arc" "_C" '(91.97531250 0.50000000) "@81.97683734<171" "_A" "9") (ssadd (entlast) azt_sruba_scalenie)
(command "_line" '(10.00000000 19.91250000) '(10.00000000 0.00000000) "") (ssadd (entlast) azt_sruba_scalenie)
(command "_line" '(10.00000000 -19.91250000) '(10.00000000 19.91250000) "") (ssadd (entlast) azt_sruba_scalenie)
(command "_line" '(34.00000000 0.00000000) '(34.00000000 19.91250000) "") (ssadd (entlast) azt_sruba_scalenie)
(command "_line" '(33.00000000 -13.27500000) '(11.00000000 -13.27500000) "") (ssadd (entlast) azt_sruba_scalenie)
(command "_line" '(11.00000000 -13.27500000) '(33.00000000 -13.27500000) "") (ssadd (entlast) azt_sruba_scalenie)
(command "_arc" "_C" '(32.52820313 -19.91250000) "@22.52820313<163" "_A" "34") (ssadd (entlast) azt_sruba_scalenie)
(command "_line" '(10.00000000 15.50000000) '(10.00000000 15.00000000) "") (ssadd (entlast) azt_sruba_scalenie)
(command "_line" '(10.00000000 0.00000000) '(10.00000000 15.50000000) "") (ssadd (entlast) azt_sruba_scalenie)
(command "_arc" "_C" '(91.97531250 -0.50000000) "@81.97683734<180" "_A" "9") (ssadd (entlast) azt_sruba_scalenie)
(command "_line" '(34.00000000 -19.91250000) '(34.00000000 0.00000000) "") (ssadd (entlast) azt_sruba_scalenie)
(command "_line" '(34.00000000 -15.00000000) '(34.00000000 -19.91250000) "") (ssadd (entlast) azt_sruba_scalenie)
(command "_line" '(34.00000000 19.91250000) '(34.00000000 15.00000000) "") (ssadd (entlast) azt_sruba_scalenie)
(command "_line" '(33.00000000 -26.55000000) '(11.00000000 -26.55000000) "") (ssadd (entlast) azt_sruba_scalenie)
(command "_arc" "_C" '(11.47179687 -19.91250000) "@22.52820313<343" "_A" "34") (ssadd (entlast) azt_sruba_scalenie)
(command "_arc" "_C" '(-47.97531250 -0.50000000) "@81.97683734<351" "_A" "9") (ssadd (entlast) azt_sruba_scalenie)
)

(defun azt_rysuj_gwint_m30 ()
(command "_line" '(68.00000000 15.00000000) '(70.00000000 13.00000000) "") (ssadd (entlast) azt_sruba_scalenie)
(command "_line" '(34.00000000 15.00000000) '(68.00000000 15.00000000) "") (ssadd (entlast) azt_sruba_scalenie)
(command "_line" '(70.00000000 13.00000000) '(70.00000000 -13.00000000) "") (ssadd (entlast) azt_sruba_scalenie)
(command "_line" '(68.00000000 -15.00000000) '(34.00000000 -15.00000000) "") (ssadd (entlast) azt_sruba_scalenie)
(command "_line" '(70.00000000 -13.00000000) '(68.00000000 -15.00000000) "") (ssadd (entlast) azt_sruba_scalenie)
)

(defun azt_rysuj_niewidoczna_czesc_sruby_m30 ()
(command "_line" '(4.00000000 -13.00000000) '(2.00000000 -15.00000000) "") (ssadd (entlast) azt_sruba_scalenie)
(command "_line" '(2.00000000 -15.00000000) '(4.00000000 -13.00000000) "") (ssadd (entlast) azt_sruba_scalenie)
(command "_line" '(4.00000000 -13.00000000) '(4.00000000 -15.00000000) "") (ssadd (entlast) azt_sruba_scalenie)
(command "_line" '(4.00000000 13.00000000) '(4.00000000 -13.00000000) "") (ssadd (entlast) azt_sruba_scalenie)
(command "_line" '(2.00000000 15.00000000) '(4.00000000 13.00000000) "") (ssadd (entlast) azt_sruba_scalenie)
(command "_line" '(4.00000000 13.00000000) '(4.00000000 15.00000000) "") (ssadd (entlast) azt_sruba_scalenie)
(command "_line" '(4.00000000 15.00000000) '(4.00000000 13.00000000) "") (ssadd (entlast) azt_sruba_scalenie)
(command "_line" '(4.00000000 -15.00000000) '(4.00000000 -13.00000000) "") (ssadd (entlast) azt_sruba_scalenie)
(command "_line" '(68.00000000 15.00000000) '(68.00000000 13.00000000) "") (ssadd (entlast) azt_sruba_scalenie)
(command "_line" '(68.00000000 13.00000000) '(70.00000000 13.00000000) "") (ssadd (entlast) azt_sruba_scalenie)
(command "_line" '(70.00000000 13.00000000) '(4.00000000 13.00000000) "") (ssadd (entlast) azt_sruba_scalenie)
(command "_line" '(68.00000000 -15.00000000) '(68.00000000 15.00000000) "") (ssadd (entlast) azt_sruba_scalenie)
(command "_line" '(4.00000000 -13.00000000) '(70.00000000 -13.00000000) "") (ssadd (entlast) azt_sruba_scalenie)
(command "_line" '(70.00000000 -13.00000000) '(68.00000000 -13.00000000) "") (ssadd (entlast) azt_sruba_scalenie)
(command "_line" '(68.00000000 -13.00000000) '(68.00000000 -15.00000000) "") (ssadd (entlast) azt_sruba_scalenie)
)

(defun c:azt_sruba_widok_m30 ()
  (setq azt_sruba_scalenie (ssadd))
  (setq azt_aktualna_sruba_widok_typ "30")
  (azt_przywroc_ucs_sruby)
  (azt_punkty_skleszczenia_sruby)
  (azt_skleszczenie_sruby)
  (command "_ZOOM" "_SCALE" "10000X")
  (azt_ucs_sruby)
  (command "_layer" "_S" "S_VIEW" "")
  (setvar "CECOLOR" "BYLAYER")
  (azt_rysuj_leb_m30)
  (setvar "CECOLOR" "126")
  (azt_rysuj_trzpien_m30)
  (setvar "CECOLOR" "127")
  (azt_rysuj_niewidoczna_czesc_sruby_m30)
  (setvar "CECOLOR" "128")
  (azt_rysuj_podkladki_m30)
  (azt_rysuj_nakretke_m30)
  (azt_rysuj_gwint_m30)
  (azt_wprowadz_skleszczenie_sruby)
  (azt_przywroc_ucs_sruby)
  (command "_ZOOM" "_SCALE" "0.0001X")
  (command "_layer" "_S" "0" "")
  (setvar "CECOLOR" "BYLAYER")
  (command "_group" "_C" "*" "" azt_sruba_scalenie "")
  (setq azt_sruba_scalenie (ssadd))
)

;#######################   SRUBA M30 - GWINT   #######################

(defun azt_rysuj_gwint_przekr_m30 ()
(command "_line" '(-23.00000000 -13.27500000) '(0.00000000 -26.55000000) "") (ssadd (entlast) azt_sruba_scalenie)
(command "_line" '(0.00000000 -26.55000000) '(23.00000000 -13.27500000) "") (ssadd (entlast) azt_sruba_scalenie)
(command "_line" '(0.00000000 26.55000000) '(-23.00000000 13.27500000) "") (ssadd (entlast) azt_sruba_scalenie)
(command "_line" '(-23.00000000 13.27500000) '(-23.00000000 -13.27500000) "") (ssadd (entlast) azt_sruba_scalenie)
(command "_line" '(23.00000000 -13.27500000) '(23.00000000 13.27500000) "") (ssadd (entlast) azt_sruba_scalenie)
(command "_circle" '(0.00000000 0.00000000) "15.00000000") (ssadd (entlast) azt_sruba_scalenie)
(command "_circle" '(0.00000000 0.00000000) "28.00000000") (ssadd (entlast) azt_sruba_scalenie)
(command "_line" '(23.00000000 13.27500000) '(0.00000000 26.55000000) "") (ssadd (entlast) azt_sruba_scalenie)
(command "_circle" '(0.00000000 0.00000000) "22.00000000") (ssadd (entlast) azt_sruba_scalenie)
)

(defun azt_rysuj_osie_gwint_przekr_m30 ()
(command "_line" '(0.00000000 0.00000000) '(32.20000000 0.00000000) "") (ssadd (entlast) azt_sruba_scalenie)
(command "_line" '(-32.20000000 0.00000000) '(0.00000000 0.00000000) "") (ssadd (entlast) azt_sruba_scalenie)
(command "_line" '(0.00000000 0.00000000) '(0.00000000 -37.17000000) "") (ssadd (entlast) azt_sruba_scalenie)
(command "_line" '(0.00000000 37.17000000) '(0.00000000 0.00000000) "") (ssadd (entlast) azt_sruba_scalenie)
)

(defun c:azt_sruba_gwint_m30 ()
(setq azt_sruba_scalenie (ssadd))
(setq azt_aktualna_sruba_gwint_typ "30")
(azt_punkt_wstawienia_sruby_przekr)
(command "_ZOOM" "_SCALE" "10000X")
(azt_ucs_wstawienia_sruby_przekr)
(command "_layer" "_S" "S_VIEW" "")
(azt_rysuj_gwint_przekr_m30)
(command "_layer" "_S" "S_GRIDS" "")
(azt_rysuj_osie_gwint_przekr_m30)
(azt_przywroc_ucs_sruby)
(command "_ZOOM" "_SCALE" "0.0001X")
(command "_layer" "_S" "0" "")
(command "_group" "_C" "*" "" azt_sruba_scalenie "")
(setq azt_sruba_scalenie (ssadd))
)

;#######################   SRUBA M30 - LEB   #######################

(defun azt_rysuj_leb_przekr_m30 ()
(command "_line" '(-23.00000000 -13.27500000) '(0.00000000 -26.55000000) "") (ssadd (entlast) azt_sruba_scalenie)
(command "_line" '(-23.00000000 13.27500000) '(-23.00000000 -13.27500000) "") (ssadd (entlast) azt_sruba_scalenie)
(command "_line" '(0.00000000 26.55000000) '(-23.00000000 13.27500000) "") (ssadd (entlast) azt_sruba_scalenie)
(command "_line" '(0.00000000 -26.55000000) '(23.00000000 -13.27500000) "") (ssadd (entlast) azt_sruba_scalenie)
(command "_circle" '(0.00000000 0.00000000) "22.00000000") (ssadd (entlast) azt_sruba_scalenie)
(command "_line" '(23.00000000 13.27500000) '(0.00000000 26.55000000) "") (ssadd (entlast) azt_sruba_scalenie)
(command "_line" '(23.00000000 -13.27500000) '(23.00000000 13.27500000) "") (ssadd (entlast) azt_sruba_scalenie)
)

(defun azt_rysuj_osie_leb_przekr_m30 ()
(command "_line" '(0.00000000 0.00000000) '(32.20000000 0.00000000) "") (ssadd (entlast) azt_sruba_scalenie)
(command "_line" '(-32.20000000 0.00000000) '(0.00000000 0.00000000) "") (ssadd (entlast) azt_sruba_scalenie)
(command "_line" '(0.00000000 0.00000000) '(0.00000000 -37.17000000) "") (ssadd (entlast) azt_sruba_scalenie)
(command "_line" '(0.00000000 37.17000000) '(0.00000000 0.00000000) "") (ssadd (entlast) azt_sruba_scalenie)
)

(defun c:azt_sruba_leb_m30 ()
(setq azt_sruba_scalenie (ssadd))
(setq azt_aktualna_sruba_leb_typ "30")
(azt_punkt_wstawienia_sruby_przekr)
(command "_ZOOM" "_SCALE" "10000X")
(azt_ucs_wstawienia_sruby_przekr)
(command "_layer" "_S" "S_VIEW" "")
(azt_rysuj_leb_przekr_m30)
(command "_layer" "_S" "S_GRIDS" "")
(azt_rysuj_osie_leb_przekr_m30)
(azt_przywroc_ucs_sruby)
(command "_ZOOM" "_SCALE" "0.0001X")
(command "_layer" "_S" "0" "")
(command "_group" "_C" "*" "" azt_sruba_scalenie "")
(setq azt_sruba_scalenie (ssadd))
)

;#######################   KONIEC SRUBY M30   #######################

;#######################   SRUBY - KONIEC  ##########################

;#######################   PROFILE - POCZATEK  #######################

(defun c:azt_wczytaj_baze_profili_stalowych ()
  (vl-cmdf "_.-insert" "C:\\AZT\\TEMPLATES\\SZABLON_PROFILI_STALOWYCH.dwg" '(0. 0. 0.) "" "" "")
  (vl-cmdf "_.erase" (entlast) "")
  (vl-cmdf "_.-purge" "Blocks" "SZABLON_PROFILI_STALOWYCH" "_N")
  (vl-cmdf "_.-purge" "Blocks" "AZT_PROFIL_WIDOK" "_N")
  (princ)
)

(defun c:azt_profil_widok_gora ()
  (setq azt_rodzina_profil_widok (getstring (strcat "\nWybierz rodzine profilu [HEA/HEB/UPE/L/RHS]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)

;###############################
;###############################
;###############################

(defun azt_aktualna_rodzina_profil_widok_funkcja ()
(setq azt_profil_widok_lista (vl-directory-files "C:\\AZT\\DATA\\STEEL\\AZT_PL_WID" "HEA*.mln")) ; Lista plikow
(setq azt_profil_widok_lista_wybor "[")
(setq i 0)
(foreach file azt_profil_widok_lista
  (setq i (1+ i))
  (setq azt_profil_widok_lista_wybor (strcat azt_profil_widok_lista_wybor (vl-string-trim "HEA" (vl-filename-base file))))
  (if (< i (length azt_profil_widok_lista))
    (setq azt_profil_widok_lista_wybor (strcat azt_profil_widok_lista_wybor "/"))
  )
)
(setq azt_profil_widok_lista_wybor (strcat azt_profil_widok_lista_wybor "]"))
(setq azt_typ_profil_widok (getstring (strcat "\nWybierz typ profilu " azt_profil_widok_lista_wybor ": <" azt_aktualny_typ_profil_widok ">")))
)

(if (equal azt_aktualna_rodzina_profil_widok "HEA")
(azt_aktualna_rodzina_profil_widok_funkcja)
(princ)
)

;###############################
;###############################
;###############################


  (if (equal azt_typ_profil_widok "")
      (setq azt_typ_profil_widok azt_aktualny_typ_profil_widok)
      (princ)
  )
  (setq azt_aktualny_typ_profil_widok azt_typ_profil_widok)

  
  (setq azt_profil_widok_bok_wid (strcat "AZT_PL_WID_G_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_bok_wid ()
  (setq azt_rodzina_profil_widok (getstring (strcat "\nWybierz rodzine profilu [HEA/HEB/UPE/L/RHS]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)
  
  (setq azt_typ_profil_widok (getstring (strcat "\nWybierz typ profilu [100/120/200]: <" azt_aktualny_typ_profil_widok ">")))
  (if (equal azt_typ_profil_widok "")
      (setq azt_typ_profil_widok azt_aktualny_typ_profil_widok)
      (princ)
  )
  (setq azt_aktualny_typ_profil_widok azt_typ_profil_widok)
  
  (setq azt_profil_widok_bok_wid (strcat "AZT_PL_WID_B_W_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_bok_nwid ()
  (setq azt_rodzina_profil_widok (getstring (strcat "\nWybierz rodzine profilu [HEA/HEB/UPE/L/RHS]: <" azt_aktualna_rodzina_profil_widok ">")))
  (if (equal azt_rodzina_profil_widok "")
      (setq azt_rodzina_profil_widok azt_aktualna_rodzina_profil_widok)
      (princ)
  )
  (setq azt_aktualna_rodzina_profil_widok azt_rodzina_profil_widok)
  
  (setq azt_typ_profil_widok (getstring (strcat "\nWybierz typ profilu [100/120/200]: <" azt_aktualny_typ_profil_widok ">")))
  (if (equal azt_typ_profil_widok "")
      (setq azt_typ_profil_widok azt_aktualny_typ_profil_widok)
      (princ)
  )
  (setq azt_aktualny_typ_profil_widok azt_typ_profil_widok)
  
  (setq azt_profil_widok_bok_wid (strcat "AZT_PL_WID_B_NW_" azt_rodzina_profil_widok azt_typ_profil_widok))
  (repeat 100
  (setq azt_profil_widok_punkt1 (getpoint "\n Wskaz punkt poczatkowy: "))
  (setq azt_profil_widok_punkt2 (getpoint azt_profil_widok_punkt1 "\n Wskaz punkt koncowy: "))
  (command "_mline" "_J" "_Z" "_S" "1" "_ST" azt_profil_widok_bok_wid azt_profil_widok_punkt1 azt_profil_widok_punkt2 "")
  )
)

(defun c:azt_profil_widok_odwroc_strone ()
  (repeat 100
  (setq azt_profil_widok_odwroc_strone_obiekt (entsel))
  (command "_mirror" azt_profil_widok_odwroc_strone_obiekt "" (cdr (assoc 10 (entget (car azt_profil_widok_odwroc_strone_obiekt)))) (cdr (assoc 11 (reverse (entget (car azt_profil_widok_odwroc_strone_obiekt))))) "_Y")
  ;(command "_mirror" (entlast) "" (cdr (assoc 10 (entget (entlast)))) (cdr (assoc 11 (reverse (entget (entlast))))) "_Y")
  )
  (princ)
)

;#######################   PROFILE - KONIEC  #######################

(azt_sruba_start)
(azt_profil_widok_start)
